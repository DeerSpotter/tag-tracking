AddReference "System.Windows.Forms.dll"
AddReference "System.Drawing.dll"
Imports INV = Inventor
Imports WF = System.Windows.Forms
Imports SD = System.Drawing
Imports IO = System.IO
Sub Main()

    Const TAG_NS As String = "INTERNAL_CAD_TAG"
    Const TAG_KEY As String = "TagName"
    Const DATE_KEY As String = "TaggedDate"
    Const USER_KEY As String = "TaggedBy"
    Const DOC_TYPE_KEY As String = "TaggedDocumentType"

    Dim app As INV.Application = ThisApplication
    Dim activeDoc As INV.Document = app.ActiveDocument

    If activeDoc Is Nothing Then
        WF.MessageBox.Show("No active document found.", "Internal CAD Tag")
        Exit Sub
    End If

    Dim recorderFile As String = IO.Path.Combine(IO.Path.GetTempPath(), "InternalCadTag_ActionRecorder.txt")

    Dim dlg As New WF.Form()
    dlg.Text = "Internal CAD Tag Action Recorder"
    dlg.FormBorderStyle = WF.FormBorderStyle.FixedDialog
    dlg.StartPosition = WF.FormStartPosition.CenterParent
    dlg.MinimizeBox = False
    dlg.MaximizeBox = False
    dlg.Width = 940
    dlg.Height = 395

    Dim bg As SD.Color = SD.Color.FromArgb(211, 211, 211)
    dlg.BackColor = bg
    dlg.ForeColor = SD.Color.FromArgb(32, 32, 32)

    Dim leftPad As Integer = 16
    Dim y As Integer = 18

    Dim titleLbl As New WF.Label()
    titleLbl.AutoSize = True
    titleLbl.Left = leftPad
    titleLbl.Top = y
    titleLbl.Font = New SD.Font("Segoe UI", 10.0!, SD.FontStyle.Bold)
    titleLbl.Text = "Choose an action:"
    titleLbl.BackColor = SD.Color.Transparent
    dlg.Controls.Add(titleLbl)

    y += 32

    Dim tagLbl As New WF.Label()
    tagLbl.AutoSize = True
    tagLbl.Left = leftPad
    tagLbl.Top = y + 4
    tagLbl.Text = "Custom tag name:"
    tagLbl.BackColor = SD.Color.Transparent
    dlg.Controls.Add(tagLbl)

    Dim tagBox As New WF.TextBox()
    tagBox.Left = 140
    tagBox.Top = y
    tagBox.Width = 760
    tagBox.Text = "KRATOS_INTERNAL_CAD"
    dlg.Controls.Add(tagBox)

    y += 30

    Dim detectedLbl As New WF.Label()
    detectedLbl.AutoSize = True
    detectedLbl.Left = leftPad
    detectedLbl.Top = y + 4
    detectedLbl.Text = "Detected tag:"
    detectedLbl.BackColor = SD.Color.Transparent
    dlg.Controls.Add(detectedLbl)

    Dim detectedBox As New WF.TextBox()
    detectedBox.Left = 140
    detectedBox.Top = y
    detectedBox.Width = 760
    detectedBox.ReadOnly = True
    detectedBox.BackColor = SD.Color.White
    detectedBox.Text = GetDetectedTagText(activeDoc, TAG_NS, TAG_KEY)
    dlg.Controls.Add(detectedBox)

    y += 42

    Dim addBold As New WF.Label()
    addBold.AutoSize = True
    addBold.Left = leftPad
    addBold.Top = y
    addBold.Font = New SD.Font("Segoe UI", 9.5!, SD.FontStyle.Bold)
    addBold.Text = "WRITE TAG"
    addBold.BackColor = SD.Color.Transparent
    dlg.Controls.Add(addBold)

    Dim addRest As New WF.Label()
    addRest.AutoSize = True
    addRest.Left = 170
    addRest.Top = y
    addRest.Text = "Write this tag to the current part or assembly"
    addRest.BackColor = SD.Color.Transparent
    dlg.Controls.Add(addRest)

    y += 26

    Dim scanBold As New WF.Label()
    scanBold.AutoSize = True
    scanBold.Left = leftPad
    scanBold.Top = y
    scanBold.Font = New SD.Font("Segoe UI", 9.5!, SD.FontStyle.Bold)
    scanBold.Text = "CHECK TAG"
    scanBold.BackColor = SD.Color.Transparent
    dlg.Controls.Add(scanBold)

    Dim scanRest As New WF.Label()
    scanRest.AutoSize = True
    scanRest.Left = 170
    scanRest.Top = y
    scanRest.Text = "Check current assembly for this exact tag name"
    scanRest.BackColor = SD.Color.Transparent
    dlg.Controls.Add(scanRest)

    y += 26

    Dim allBold As New WF.Label()
    allBold.AutoSize = True
    allBold.Left = leftPad
    allBold.Top = y
    allBold.Font = New SD.Font("Segoe UI", 9.5!, SD.FontStyle.Bold)
    allBold.Text = "SEARCH ALL"
    allBold.BackColor = SD.Color.Transparent
    dlg.Controls.Add(allBold)

    Dim allRest As New WF.Label()
    allRest.AutoSize = True
    allRest.Left = 170
    allRest.Top = y
    allRest.Text = "Find all internal CAD tags in the current assembly"
    allRest.BackColor = SD.Color.Transparent
    dlg.Controls.Add(allRest)

    y += 26

    Dim actionBold As New WF.Label()
    actionBold.AutoSize = True
    actionBold.Left = leftPad
    actionBold.Top = y
    actionBold.Font = New SD.Font("Segoe UI", 9.5!, SD.FontStyle.Bold)
    actionBold.Text = "RECORDED ACTIONS"
    actionBold.BackColor = SD.Color.Transparent
    dlg.Controls.Add(actionBold)

    Dim actionRest As New WF.Label()
    actionRest.AutoSize = True
    actionRest.Left = 170
    actionRest.Top = y
    actionRest.Text = "Run actions against tagged files and generate replayable iLogic code"
    actionRest.BackColor = SD.Color.Transparent
    dlg.Controls.Add(actionRest)

    Dim btnWrite As New WF.Button()
    btnWrite.Text = "WRITE TAG"
    btnWrite.Width = 110
    btnWrite.Height = 30
    btnWrite.Left = 16
    btnWrite.Top = 235
    btnWrite.Tag = "WRITE_TAG"
    AddHandler btnWrite.Click, AddressOf ActionButtonClick
    dlg.Controls.Add(btnWrite)

    Dim btnRemoveTag As New WF.Button()
    btnRemoveTag.Text = "REMOVE TAG"
    btnRemoveTag.Width = 110
    btnRemoveTag.Height = 30
    btnRemoveTag.Left = 136
    btnRemoveTag.Top = 235
    btnRemoveTag.Tag = "REMOVE_TAG"
    AddHandler btnRemoveTag.Click, AddressOf ActionButtonClick
    dlg.Controls.Add(btnRemoveTag)

    Dim btnCheck As New WF.Button()
    btnCheck.Text = "CHECK TAG"
    btnCheck.Width = 110
    btnCheck.Height = 30
    btnCheck.Left = 256
    btnCheck.Top = 235
    btnCheck.Tag = "CHECK_TAG"
    AddHandler btnCheck.Click, AddressOf ActionButtonClick
    dlg.Controls.Add(btnCheck)

    Dim btnSearchAll As New WF.Button()
    btnSearchAll.Text = "SEARCH ALL"
    btnSearchAll.Width = 110
    btnSearchAll.Height = 30
    btnSearchAll.Left = 376
    btnSearchAll.Top = 235
    btnSearchAll.Tag = "SEARCH_ALL"
    AddHandler btnSearchAll.Click, AddressOf ActionButtonClick
    dlg.Controls.Add(btnSearchAll)

    Dim btnExamples As New WF.Button()
    btnExamples.Text = "CODE HELP"
    btnExamples.Width = 110
    btnExamples.Height = 30
    btnExamples.Left = 496
    btnExamples.Top = 235
    btnExamples.Tag = "CODE_HELP"
    AddHandler btnExamples.Click, AddressOf ActionButtonClick
    dlg.Controls.Add(btnExamples)

    Dim btnSuppressOcc As New WF.Button()
    btnSuppressOcc.Text = "SUPPRESS OCC"
    btnSuppressOcc.Width = 130
    btnSuppressOcc.Height = 30
    btnSuppressOcc.Left = 16
    btnSuppressOcc.Top = 280
    btnSuppressOcc.Tag = "SUPPRESS_OCC"
    AddHandler btnSuppressOcc.Click, AddressOf ActionButtonClick
    dlg.Controls.Add(btnSuppressOcc)

    Dim btnUnsuppressOcc As New WF.Button()
    btnUnsuppressOcc.Text = "UNSUPPRESS OCC"
    btnUnsuppressOcc.Width = 140
    btnUnsuppressOcc.Height = 30
    btnUnsuppressOcc.Left = 156
    btnUnsuppressOcc.Top = 280
    btnUnsuppressOcc.Tag = "UNSUPPRESS_OCC"
    AddHandler btnUnsuppressOcc.Click, AddressOf ActionButtonClick
    dlg.Controls.Add(btnUnsuppressOcc)

    Dim btnSuppressFeature As New WF.Button()
    btnSuppressFeature.Text = "SUPPRESS FEATURE"
    btnSuppressFeature.Width = 150
    btnSuppressFeature.Height = 30
    btnSuppressFeature.Left = 306
    btnSuppressFeature.Top = 280
    btnSuppressFeature.Tag = "SUPPRESS_FEATURE"
    AddHandler btnSuppressFeature.Click, AddressOf ActionButtonClick
    dlg.Controls.Add(btnSuppressFeature)

    Dim btnUnsuppressFeature As New WF.Button()
    btnUnsuppressFeature.Text = "UNSUPPRESS FEATURE"
    btnUnsuppressFeature.Width = 165
    btnUnsuppressFeature.Height = 30
    btnUnsuppressFeature.Left = 466
    btnUnsuppressFeature.Top = 280
    btnUnsuppressFeature.Tag = "UNSUPPRESS_FEATURE"
    AddHandler btnUnsuppressFeature.Click, AddressOf ActionButtonClick
    dlg.Controls.Add(btnUnsuppressFeature)

    Dim btnShowCode As New WF.Button()
    btnShowCode.Text = "SHOW GENERATED CODE"
    btnShowCode.Width = 180
    btnShowCode.Height = 30
    btnShowCode.Left = 641
    btnShowCode.Top = 280
    btnShowCode.Tag = "SHOW_GENERATED_CODE"
    AddHandler btnShowCode.Click, AddressOf ActionButtonClick
    dlg.Controls.Add(btnShowCode)

    Dim btnClear As New WF.Button()
    btnClear.Text = "CLEAR STEPS"
    btnClear.Width = 120
    btnClear.Height = 30
    btnClear.Left = 16
    btnClear.Top = 325
    btnClear.Tag = "CLEAR_STEPS"
    AddHandler btnClear.Click, AddressOf ActionButtonClick
    dlg.Controls.Add(btnClear)

    Dim btnCancel As New WF.Button()
    btnCancel.Text = "Cancel"
    btnCancel.Width = 100
    btnCancel.Height = 30
    btnCancel.Left = 820
    btnCancel.Top = 325
    btnCancel.Tag = "CANCEL"
    AddHandler btnCancel.Click, AddressOf ActionButtonClick
    dlg.Controls.Add(btnCancel)

    dlg.AcceptButton = btnWrite
    dlg.CancelButton = btnCancel

    dlg.ShowDialog()

    If dlg.Tag Is Nothing Then Exit Sub

    Dim actionName As String = CStr(dlg.Tag)

    If actionName = "CANCEL" Then Exit Sub

    Dim customTag As String = tagBox.Text.Trim()

    If actionName <> "SEARCH_ALL" AndAlso actionName <> "CODE_HELP" AndAlso actionName <> "SHOW_GENERATED_CODE" AndAlso actionName <> "CLEAR_STEPS" AndAlso actionName <> "REMOVE_TAG" Then
        If String.IsNullOrWhiteSpace(customTag) Then
            WF.MessageBox.Show("Enter a custom tag name first.", "Internal CAD Tag")
            Exit Sub
        End If
    End If

    If IsRecordingAction(actionName) Then
        If Not ConfirmClearPreviousRecordedStepsIfNeeded(recorderFile) Then Exit Sub
    End If

    If actionName = "WRITE_TAG" Then

        If activeDoc.DocumentType = INV.DocumentTypeEnum.kPartDocumentObject Then

            Dim part As INV.PartDocument = TryCast(activeDoc, INV.PartDocument)

            If part Is Nothing Then
                WF.MessageBox.Show("Could not read active part document.", "Internal CAD Tag")
                Exit Sub
            End If

            WriteFullTag(part, part.ComponentDefinition, TAG_NS, TAG_KEY, DATE_KEY, USER_KEY, DOC_TYPE_KEY, customTag, "Part")
            part.Save()

            WF.MessageBox.Show("Tag written to current part:" & vbCrLf & vbCrLf & customTag, "Internal CAD Tag")

        ElseIf activeDoc.DocumentType = INV.DocumentTypeEnum.kAssemblyDocumentObject Then

            Dim asm As INV.AssemblyDocument = TryCast(activeDoc, INV.AssemblyDocument)

            If asm Is Nothing Then
                WF.MessageBox.Show("Could not read active assembly document.", "Internal CAD Tag")
                Exit Sub
            End If

            WriteFullTag(asm, asm.ComponentDefinition, TAG_NS, TAG_KEY, DATE_KEY, USER_KEY, DOC_TYPE_KEY, customTag, "Assembly")
            asm.Save()

            WF.MessageBox.Show("Tag written to current assembly:" & vbCrLf & vbCrLf & customTag, "Internal CAD Tag")

        Else

            WF.MessageBox.Show("Only part and assembly documents are supported.", "Internal CAD Tag")
            Exit Sub

        End If

    ElseIf actionName = "REMOVE_TAG" Then

        Dim removeScope As String = ShowRemoveTagScopeForm()

        If String.IsNullOrWhiteSpace(removeScope) Then Exit Sub

        If removeScope = "SPECIFIC" Then

            Dim removedCount As Integer = RemoveTagFromSpecificComponent(activeDoc, TAG_NS)

            WF.MessageBox.Show("Tag removal complete." & vbCrLf & vbCrLf & _
                               "Scope: Current open file only" & vbCrLf & _
                               "Removed tag locations: " & removedCount.ToString() & vbCrLf & vbCrLf & _
                               "Note: each file can contain up to 2 tag locations:" & vbCrLf & _
                               "1. Document level" & vbCrLf & _
                               "2. Component definition level", _
                               "Internal CAD Tag")

        ElseIf removeScope = "ALL" Then

            Dim topAsm As INV.AssemblyDocument = TryCast(activeDoc, INV.AssemblyDocument)

            If topAsm Is Nothing Then
                WF.MessageBox.Show("Open an assembly file before removing tags from all components.", "Internal CAD Tag")
                Exit Sub
            End If

            Dim removedCount As Integer = RemoveTagsFromAllComponents(topAsm, TAG_NS)

            WF.MessageBox.Show("Tag removal complete." & vbCrLf & vbCrLf & _
                               "Scope: Current assembly and all referenced parts and assemblies" & vbCrLf & _
                               "Removed tag locations: " & removedCount.ToString() & vbCrLf & vbCrLf & _
                               "This number is tag locations removed, not file count." & vbCrLf & _
                               "Each part or assembly can contain up to 2 tag locations:" & vbCrLf & _
                               "1. Document level" & vbCrLf & _
                               "2. Component definition level", _
                               "Internal CAD Tag")

        End If

    ElseIf actionName = "CHECK_TAG" Then

        Dim topAsm As INV.AssemblyDocument = TryCast(activeDoc, INV.AssemblyDocument)

        If topAsm Is Nothing Then
            WF.MessageBox.Show("Open an assembly file before using CHECK TAG.", "Internal CAD Tag")
            Exit Sub
        End If

        SearchExactTag(topAsm, TAG_NS, TAG_KEY, DATE_KEY, USER_KEY, DOC_TYPE_KEY, customTag)

    ElseIf actionName = "SEARCH_ALL" Then

        Dim topAsm As INV.AssemblyDocument = TryCast(activeDoc, INV.AssemblyDocument)

        If topAsm Is Nothing Then
            WF.MessageBox.Show("Open an assembly file before using SEARCH ALL.", "Internal CAD Tag")
            Exit Sub
        End If

        SearchAllTags(topAsm, TAG_NS, TAG_KEY, DATE_KEY, USER_KEY, DOC_TYPE_KEY)

    ElseIf actionName = "CODE_HELP" Then

        ShowCodeHelp(TAG_NS, TAG_KEY)

    ElseIf actionName = "SUPPRESS_OCC" Then

        Dim topAsm As INV.AssemblyDocument = TryCast(activeDoc, INV.AssemblyDocument)

        If topAsm Is Nothing Then
            WF.MessageBox.Show("Open an assembly file before using SUPPRESS OCC.", "Internal CAD Tag")
            Exit Sub
        End If

        Dim pickedOcc As INV.ComponentOccurrence = PickAssemblyOccurrence("Select the occurrence to suppress by tag.")

        If pickedOcc Is Nothing Then Exit Sub

        Dim effectiveTag As String = ResolveEffectiveTagForSelectedOccurrence(pickedOcc, TAG_NS, TAG_KEY, DATE_KEY, USER_KEY, DOC_TYPE_KEY, customTag)

        If String.IsNullOrWhiteSpace(effectiveTag) Then Exit Sub

        Dim count As Integer = SuppressOccurrencesByTag(topAsm.ComponentDefinition.Occurrences, TAG_NS, TAG_KEY, effectiveTag)

        AppendRecorderStep(recorderFile, "SUPPRESS_OCC|" & effectiveTag)

'        WF.MessageBox.Show("Selected occurrence tag: " & effectiveTag & vbCrLf & vbCrLf & _
'                           "Suppressed matching occurrences: " & count.ToString() & vbCrLf & vbCrLf & _
'                           "Step recorded.", _
'                           "Internal CAD Tag")

    ElseIf actionName = "UNSUPPRESS_OCC" Then

        Dim topAsm As INV.AssemblyDocument = TryCast(activeDoc, INV.AssemblyDocument)

        If topAsm Is Nothing Then
            WF.MessageBox.Show("Open an assembly file before using UNSUPPRESS OCC.", "Internal CAD Tag")
            Exit Sub
        End If

        Dim effectiveTag As String = ShowUnsuppressTagSourceForm(customTag)

        If String.IsNullOrWhiteSpace(effectiveTag) Then Exit Sub

        If effectiveTag = "__SELECT_OCCURRENCE__" Then

            Dim pickedOcc As INV.ComponentOccurrence = PickAssemblyOccurrence("Select one occurrence that has the tag you want to unsuppress.")

            If pickedOcc Is Nothing Then Exit Sub

            effectiveTag = ResolveEffectiveTagForSelectedOccurrenceForSingleUnsuppress(pickedOcc, TAG_NS, TAG_KEY, DATE_KEY, USER_KEY, DOC_TYPE_KEY, customTag)

            If String.IsNullOrWhiteSpace(effectiveTag) Then Exit Sub

        End If

        Dim count As Integer = UnsuppressOccurrencesByTagSafe(topAsm.ComponentDefinition.Occurrences, TAG_NS, TAG_KEY, effectiveTag)

        AppendRecorderStep(recorderFile, "UNSUPPRESS_OCC|" & effectiveTag)

        Try
            topAsm.Update()
            topAsm.Save()
        Catch
        End Try

'        WF.MessageBox.Show("Unsuppressed matching tagged occurrences and recorded the tag based replay step." & vbCrLf & vbCrLf & _
'                           "Tag: " & effectiveTag & vbCrLf & _
'                           "Unsuppressed occurrences: " & count.ToString(), _
'                           "Internal CAD Tag")

    ElseIf actionName = "SUPPRESS_FEATURE" Then

        Dim p As INV.PartDocument = TryCast(activeDoc, INV.PartDocument)

        If p Is Nothing Then
            WF.MessageBox.Show("Open the part file first, then select the feature from the model tree.", "Internal CAD Tag")
            Exit Sub
        End If

        Dim effectiveTag As String = ResolveEffectiveTagForActiveFile(activeDoc, TAG_NS, TAG_KEY, customTag)

        If String.IsNullOrWhiteSpace(effectiveTag) Then Exit Sub

        Dim pickedFeature As Object = PickPartFeature("Select the feature to suppress from the model tree.")

        If pickedFeature Is Nothing Then Exit Sub

        Dim featureName As String = GetFeatureName(pickedFeature)

        If String.IsNullOrWhiteSpace(featureName) Then
            WF.MessageBox.Show("Could not read selected feature name.", "Internal CAD Tag")
            Exit Sub
        End If

        Dim suppressCount As Integer = 0

        Try
            Feature.IsActive(featureName) = False
            suppressCount = 1
        Catch
            suppressCount = 0
        End Try

        If suppressCount > 0 Then
            Try
                p.Update()
                p.Save()
            Catch
            End Try

            AppendRecorderStep(recorderFile, "SUPPRESS_FEATURE|" & effectiveTag & "|" & featureName)

'            WF.MessageBox.Show("Tagged feature suppressed and step recorded." & vbCrLf & vbCrLf & _
'                               "Tag: " & effectiveTag & vbCrLf & _
'                               "Feature: " & featureName, _
'                               "Internal CAD Tag")
        Else
            WF.MessageBox.Show("Feature was selected, but Inventor did not suppress it." & vbCrLf & vbCrLf & _
                               "Feature: " & featureName, _
                               "Internal CAD Tag")
        End If

    ElseIf actionName = "UNSUPPRESS_FEATURE" Then

        Dim p As INV.PartDocument = TryCast(activeDoc, INV.PartDocument)

        If p Is Nothing Then
            WF.MessageBox.Show("Open the part file first, then select the feature from the model tree.", "Internal CAD Tag")
            Exit Sub
        End If

        Dim effectiveTag As String = ResolveEffectiveTagForActiveFile(activeDoc, TAG_NS, TAG_KEY, customTag)

        If String.IsNullOrWhiteSpace(effectiveTag) Then Exit Sub

        Dim pickedFeature As Object = PickPartFeature("Select the feature to unsuppress from the model tree.")

        If pickedFeature Is Nothing Then Exit Sub

        Dim featureName As String = GetFeatureName(pickedFeature)

        If String.IsNullOrWhiteSpace(featureName) Then
            WF.MessageBox.Show("Could not read selected feature name.", "Internal CAD Tag")
            Exit Sub
        End If

        Dim unsuppressCount As Integer = 0

        Try
            Feature.IsActive(featureName) = True
            unsuppressCount = 1
        Catch
            unsuppressCount = 0
        End Try

        If unsuppressCount > 0 Then
            Try
                p.Update()
                p.Save()
            Catch
            End Try

            AppendRecorderStep(recorderFile, "UNSUPPRESS_FEATURE|" & effectiveTag & "|" & featureName)

'            WF.MessageBox.Show("Tagged feature unsuppressed and step recorded." & vbCrLf & vbCrLf & _
'                               "Tag: " & effectiveTag & vbCrLf & _
'                               "Feature: " & featureName, _
'                               "Internal CAD Tag")
        Else
            WF.MessageBox.Show("Feature was selected, but Inventor did not unsuppress it." & vbCrLf & vbCrLf & _
                               "Feature: " & featureName, _
                               "Internal CAD Tag")
        End If

    ElseIf actionName = "SHOW_GENERATED_CODE" Then

        ShowGeneratedCodeFromRecorder(recorderFile, TAG_NS, TAG_KEY)

    ElseIf actionName = "CLEAR_STEPS" Then

        If IO.File.Exists(recorderFile) Then
            IO.File.Delete(recorderFile)
        End If

        WF.MessageBox.Show("Recorded steps cleared.", "Internal CAD Tag")

    End If

End Sub

Private Function PickAssemblyOccurrence(prompt As String) As INV.ComponentOccurrence

    Dim picked As Object = Nothing

    Try
        picked = ThisApplication.CommandManager.Pick(INV.SelectionFilterEnum.kAssemblyOccurrenceFilter, prompt)
    Catch
        picked = Nothing
    End Try

    Dim occ As INV.ComponentOccurrence = TryCast(picked, INV.ComponentOccurrence)

    PickAssemblyOccurrence = occ

End Function

Private Function ShowUnsuppressTagSourceForm(defaultTag As String) As String

    Dim f As New WF.Form()
    f.Text = "Unsuppress Occurrence By Tag"
    f.FormBorderStyle = WF.FormBorderStyle.FixedDialog
    f.StartPosition = WF.FormStartPosition.CenterParent
    f.MinimizeBox = False
    f.MaximizeBox = False
    f.Width = 520
    f.Height = 210

    Dim lbl As New WF.Label()
    lbl.Left = 12
    lbl.Top = 14
    lbl.Width = 480
    lbl.Height = 36
    lbl.Text = "Select one occurrence to read its tag, or type the tag directly."
    f.Controls.Add(lbl)

    Dim tagLbl As New WF.Label()
    tagLbl.Left = 12
    tagLbl.Top = 60
    tagLbl.Width = 90
    tagLbl.Text = "Tag:"
    f.Controls.Add(tagLbl)

    Dim tagBox As New WF.TextBox()
    tagBox.Left = 105
    tagBox.Top = 56
    tagBox.Width = 380
    tagBox.Text = defaultTag
    f.Controls.Add(tagBox)

    Dim btnUseTyped As New WF.Button()
    btnUseTyped.Text = "Use Typed Tag"
    btnUseTyped.Width = 120
    btnUseTyped.Height = 30
    btnUseTyped.Left = 12
    btnUseTyped.Top = 115
    btnUseTyped.Tag = "USE_TYPED"
    AddHandler btnUseTyped.Click, AddressOf UnsuppressTagSourceButtonClick
    f.Controls.Add(btnUseTyped)

    Dim btnSelect As New WF.Button()
    btnSelect.Text = "Select Occurrence"
    btnSelect.Width = 140
    btnSelect.Height = 30
    btnSelect.Left = 145
    btnSelect.Top = 115
    btnSelect.Tag = "SELECT_OCCURRENCE"
    AddHandler btnSelect.Click, AddressOf UnsuppressTagSourceButtonClick
    f.Controls.Add(btnSelect)

    Dim btnCancel As New WF.Button()
    btnCancel.Text = "Cancel"
    btnCancel.Width = 100
    btnCancel.Height = 30
    btnCancel.Left = 385
    btnCancel.Top = 115
    btnCancel.Tag = "CANCEL"
    AddHandler btnCancel.Click, AddressOf UnsuppressTagSourceButtonClick
    f.Controls.Add(btnCancel)

    f.ShowDialog()

    If f.Tag Is Nothing Then Return ""

    Dim actionText As String = CStr(f.Tag)

    If actionText = "CANCEL" Then Return ""

    If actionText = "SELECT_OCCURRENCE" Then
        Return "__SELECT_OCCURRENCE__"
    End If

    Dim typedTag As String = tagBox.Text.Trim()

    If String.IsNullOrWhiteSpace(typedTag) Then
        WF.MessageBox.Show("Type a tag first, or choose Select Occurrence.", "Internal CAD Tag")
        Return ""
    End If

    Return typedTag

End Function

Private Sub UnsuppressTagSourceButtonClick(sender As Object, E As System.EventArgs)

    Dim btn As WF.Button = TryCast(sender, WF.Button)

    If btn Is Nothing Then Exit Sub

    Dim f As WF.Form = btn.FindForm()

    If f Is Nothing Then Exit Sub

    f.Tag = CStr(btn.Tag)
    f.Close()

End Sub

Private Function UnsuppressOccurrencesByTagSafe(occs As INV.ComponentOccurrences, tagNs As String, tagKey As String, wantedTag As String) As Integer

    Dim targets As New System.Collections.ArrayList()

    CollectOccurrencesByTag(occs, tagNs, tagKey, wantedTag, targets)

    Return ApplyQueuedMatchedTaggedOccurrencesActive(targets, True)

End Function

Private Sub CollectOccurrencesByTag(occs As INV.ComponentOccurrences, tagNs As String, tagKey As String, wantedTag As String, targets As System.Collections.ArrayList)

    If occs Is Nothing Then Exit Sub
    If targets Is Nothing Then Exit Sub

    Dim occ As INV.ComponentOccurrence

    For Each occ In occs

        Dim occDoc As INV.Document = GetOccurrenceDocumentSafe(occ)

        If occDoc IsNot Nothing Then

            If HasTagValue(occDoc, tagNs, tagKey, wantedTag) OrElse HasComponentDefinitionTagValue(occDoc, tagNs, tagKey, wantedTag) Then

                targets.Add(occ)

            ElseIf occDoc.DocumentType = INV.DocumentTypeEnum.kAssemblyDocumentObject Then

                Dim subDef As INV.AssemblyComponentDefinition = Nothing

                Try
                    subDef = TryCast(occ.Definition, INV.AssemblyComponentDefinition)
                Catch
                    subDef = Nothing
                End Try

                If subDef IsNot Nothing Then
                    CollectOccurrencesByTag(subDef.Occurrences, tagNs, tagKey, wantedTag, targets)
                End If

            End If

        End If

    Next

End Sub

Private Function ApplyQueuedMatchedTaggedOccurrencesActive(targets As System.Collections.ArrayList, activeState As Boolean) As Integer

    If targets Is Nothing Then Return 0
    If targets.Count = 0 Then Return 0

    Dim app As INV.Application = ThisApplication
    Dim asmDoc As INV.AssemblyDocument = TryCast(app.ActiveDocument, INV.AssemblyDocument)

    If asmDoc Is Nothing Then Return 0

    Dim asmDef As INV.AssemblyComponentDefinition = asmDoc.ComponentDefinition
    Dim isIAssemblyFactory As Boolean = False

    Try
        isIAssemblyFactory = asmDef.IsiAssemblyFactory
    Catch
        isIAssemblyFactory = False
    End Try

    If Not isIAssemblyFactory Then

        Dim normalCount As Integer = 0
        Dim obj As Object

        For Each obj In targets

            Dim occ As INV.ComponentOccurrence = TryCast(obj, INV.ComponentOccurrence)

            If occ Is Nothing Then Continue For

            Try
                If activeState Then
                    If occ.Suppressed Then
                        occ.Unsuppress()
                    End If
                Else
                    If Not occ.Suppressed Then
                        occ.Suppress()
                    End If
                End If
            Catch
            End Try

            Try
                If activeState Then
                    If Not occ.Suppressed Then normalCount += 1
                Else
                    If occ.Suppressed Then normalCount += 1
                End If
            Catch
            End Try

        Next

        Try
            asmDoc.Update()
            asmDoc.Save()
        Catch
        End Try

        Return normalCount

    End If

    Dim wantedExcluded As Boolean = Not activeState
    Dim needsToggle As New System.Collections.ArrayList()
    Dim alreadyCorrectCount As Integer = 0
    Dim targetObj As Object

    For Each targetObj In targets

        Dim occ As INV.ComponentOccurrence = TryCast(targetObj, INV.ComponentOccurrence)

        If occ Is Nothing Then Continue For

        Dim currentExcluded As Boolean = IsOccurrenceExcludedInActiveIAssemblyRow(occ)

        If currentExcluded = wantedExcluded Then
            alreadyCorrectCount += 1
        Else
            needsToggle.Add(occ)
        End If

    Next

    If needsToggle.Count = 0 Then
        Return alreadyCorrectCount
    End If

    Try
        asmDoc.SelectSet.Clear()

        Dim toggleObj As Object

        For Each toggleObj In needsToggle

            Dim occ As INV.ComponentOccurrence = TryCast(toggleObj, INV.ComponentOccurrence)

            If occ IsNot Nothing Then
                asmDoc.SelectSet.Select(occ)
            End If

        Next

        app.CommandManager.ControlDefinitions.Item("ExcludeCtxCmd").Execute()

        WF.Application.DoEvents()

        Try
            asmDoc.Update()
        Catch
        End Try

        Try
            asmDoc.SelectSet.Clear()
        Catch
        End Try

    Catch
        Try
            asmDoc.SelectSet.Clear()
        Catch
        End Try
    End Try

    Dim changedCount As Integer = 0
    Dim failed As New System.Collections.ArrayList()
    Dim verifyObj As Object

    For Each verifyObj In needsToggle

        Dim occ As INV.ComponentOccurrence = TryCast(verifyObj, INV.ComponentOccurrence)

        If occ Is Nothing Then Continue For

        If IsOccurrenceExcludedInActiveIAssemblyRow(occ) = wantedExcluded Then
            changedCount += 1
        Else
            failed.Add(occ)
        End If

    Next

    If failed.Count > 0 Then

        Dim failedObj As Object

        For Each failedObj In failed

            Dim occ As INV.ComponentOccurrence = TryCast(failedObj, INV.ComponentOccurrence)

            If occ Is Nothing Then Continue For

            If SetMatchedTaggedOccurrenceActive(occ, activeState) Then
                changedCount += 1
            End If

        Next

    End If

    Try
        asmDoc.Update()
        asmDoc.Save()
    Catch
    End Try

    Return alreadyCorrectCount + changedCount

End Function

Private Function GetOccurrenceDocumentSafe(occ As INV.ComponentOccurrence) As INV.Document

    If occ Is Nothing Then Return Nothing

    Dim occDoc As INV.Document = Nothing

    Try
        occDoc = occ.Definition.Document
    Catch
        occDoc = Nothing
    End Try

    If occDoc IsNot Nothing Then Return occDoc

    Try
        Dim descObj As Object = CallByName(occ, "ReferencedDocumentDescriptor", CallType.Get)

        If descObj IsNot Nothing Then

            Try
                occDoc = TryCast(CallByName(descObj, "ReferencedDocument", CallType.Get), INV.Document)
            Catch
                occDoc = Nothing
            End Try

            If occDoc IsNot Nothing Then Return occDoc

            Dim fullName As String = ""

            Try
                fullName = CStr(CallByName(descObj, "FullDocumentName", CallType.Get))
            Catch
                fullName = ""
            End Try

            If Not String.IsNullOrWhiteSpace(fullName) Then

                Try
                    occDoc = TryCast(ThisApplication.Documents.Open(fullName, False), INV.Document)
                Catch
                    occDoc = Nothing
                End Try

                If occDoc IsNot Nothing Then Return occDoc

            End If

        End If

    Catch
    End Try

    Try
        Dim fileDescObj As Object = CallByName(occ, "ReferencedFileDescriptor", CallType.Get)

        If fileDescObj IsNot Nothing Then

            Dim fileName As String = ""

            Try
                fileName = CStr(CallByName(fileDescObj, "FullFileName", CallType.Get))
            Catch
                fileName = ""
            End Try

            If Not String.IsNullOrWhiteSpace(fileName) Then

                Try
                    occDoc = TryCast(ThisApplication.Documents.Open(fileName, False), INV.Document)
                Catch
                    occDoc = Nothing
                End Try

                If occDoc IsNot Nothing Then Return occDoc

            End If

        End If

    Catch
    End Try

    Return Nothing

End Function

Private Function HasComponentDefinitionTagValue(doc As INV.Document, ns As String, key As String, wantedValue As String) As Boolean

    If doc Is Nothing Then Return False

    If doc.DocumentType = INV.DocumentTypeEnum.kPartDocumentObject Then

        Dim p As INV.PartDocument = TryCast(doc, INV.PartDocument)

        If p IsNot Nothing Then
            Return HasTagValue(p.ComponentDefinition, ns, key, wantedValue)
        End If

    ElseIf doc.DocumentType = INV.DocumentTypeEnum.kAssemblyDocumentObject Then

        Dim a As INV.AssemblyDocument = TryCast(doc, INV.AssemblyDocument)

        If a IsNot Nothing Then
            Return HasTagValue(a.ComponentDefinition, ns, key, wantedValue)
        End If

    End If

    Return False

End Function

Private Function HasComponentDefinitionTagValueMainRule(doc As INV.Document, ns As String, key As String, wantedValue As String) As Boolean

    If doc Is Nothing Then Return False

    If doc.DocumentType = INV.DocumentTypeEnum.kPartDocumentObject Then

        Dim p As INV.PartDocument = TryCast(doc, INV.PartDocument)

        If p IsNot Nothing Then
            Return HasTagValue(p.ComponentDefinition, ns, key, wantedValue)
        End If

    ElseIf doc.DocumentType = INV.DocumentTypeEnum.kAssemblyDocumentObject Then

        Dim a As INV.AssemblyDocument = TryCast(doc, INV.AssemblyDocument)

        If a IsNot Nothing Then
            Return HasTagValue(a.ComponentDefinition, ns, key, wantedValue)
        End If

    End If

    Return False

End Function

Private Function ResolveEffectiveTagForSelectedOccurrence(pickedOcc As INV.ComponentOccurrence, tagNs As String, tagKey As String, dateKey As String, userKey As String, docTypeKey As String, proposedTag As String) As String

    If pickedOcc Is Nothing Then Return ""

    Dim occDoc As INV.Document = GetDocumentFromOccurrenceSafe(pickedOcc)

    If occDoc Is Nothing Then
        WF.MessageBox.Show("Could not read the selected occurrence document." & vbCrLf & vbCrLf & _
                           "This can happen when the selected occurrence is suppressed and Inventor cannot resolve its referenced document." & vbCrLf & vbCrLf & _
                           "Try opening or resolving the referenced part once, then run this again.", _
                           "Internal CAD Tag")
        Return ""
    End If

    Dim existingTag As String = GetTagValue(occDoc, tagNs, tagKey)

    If String.IsNullOrWhiteSpace(existingTag) Then

        If occDoc.DocumentType = INV.DocumentTypeEnum.kPartDocumentObject Then

            Dim p As INV.PartDocument = TryCast(occDoc, INV.PartDocument)

            If p IsNot Nothing Then
                existingTag = GetTagValue(p.ComponentDefinition, tagNs, tagKey)
            End If

        ElseIf occDoc.DocumentType = INV.DocumentTypeEnum.kAssemblyDocumentObject Then

            Dim a As INV.AssemblyDocument = TryCast(occDoc, INV.AssemblyDocument)

            If a IsNot Nothing Then
                existingTag = GetTagValue(a.ComponentDefinition, tagNs, tagKey)
            End If

        End If

    End If

    If Not String.IsNullOrWhiteSpace(existingTag) Then
        Return existingTag
    End If

    If String.IsNullOrWhiteSpace(proposedTag) Then
        WF.MessageBox.Show("The selected occurrence does not have a tag, and no new tag name was entered." & vbCrLf & vbCrLf & _
                           "This code will abort.", _
                           "Internal CAD Tag")
        Return ""
    End If

    Dim result As WF.DialogResult = WF.MessageBox.Show("The selected occurrence does not have an internal CAD tag." & vbCrLf & vbCrLf & _
                                                       "Selected occurrence:" & vbCrLf & _
                                                       pickedOcc.Name & vbCrLf & vbCrLf & _
                                                       "New tag to write:" & vbCrLf & _
                                                       proposedTag & vbCrLf & vbCrLf & _
                                                       "Do you want to write this tag to the selected occurrence document?", _
                                                       "Internal CAD Tag", _
                                                       WF.MessageBoxButtons.YesNo, _
                                                       WF.MessageBoxIcon.Warning)

    If result <> WF.DialogResult.Yes Then
        WF.MessageBox.Show("No tag was written." & vbCrLf & vbCrLf & _
                           "This code will abort because the selected occurrence has no tag.", _
                           "Internal CAD Tag")
        Return ""
    End If

    If occDoc.DocumentType = INV.DocumentTypeEnum.kPartDocumentObject Then

        Dim p As INV.PartDocument = TryCast(occDoc, INV.PartDocument)

        If p Is Nothing Then
            WF.MessageBox.Show("Could not write tag because the selected occurrence document could not be read as a part.", "Internal CAD Tag")
            Return ""
        End If

        WriteFullTag(p, p.ComponentDefinition, tagNs, tagKey, dateKey, userKey, docTypeKey, proposedTag, "Part")

        Try
            p.Save()
        Catch
        End Try

        Return proposedTag

    ElseIf occDoc.DocumentType = INV.DocumentTypeEnum.kAssemblyDocumentObject Then

        Dim a As INV.AssemblyDocument = TryCast(occDoc, INV.AssemblyDocument)

        If a Is Nothing Then
            WF.MessageBox.Show("Could not write tag because the selected occurrence document could not be read as an assembly.", "Internal CAD Tag")
            Return ""
        End If

        WriteFullTag(a, a.ComponentDefinition, tagNs, tagKey, dateKey, userKey, docTypeKey, proposedTag, "Assembly")

        Try
            a.Save()
        Catch
        End Try

        Return proposedTag

    End If

    WF.MessageBox.Show("Only part and assembly occurrence documents are supported.", "Internal CAD Tag")

    Return ""

End Function

Private Function GetDocumentFromOccurrenceSafe(pickedOcc As INV.ComponentOccurrence) As INV.Document

    If pickedOcc Is Nothing Then Return Nothing

    Dim occDoc As INV.Document = Nothing

    Try
        occDoc = pickedOcc.Definition.Document
    Catch
        occDoc = Nothing
    End Try

    If occDoc IsNot Nothing Then Return occDoc

    Try
        Dim descObj As Object = CallByName(pickedOcc, "ReferencedDocumentDescriptor", CallType.Get)

        If descObj IsNot Nothing Then

            Try
                occDoc = TryCast(CallByName(descObj, "ReferencedDocument", CallType.Get), INV.Document)
            Catch
                occDoc = Nothing
            End Try

            If occDoc IsNot Nothing Then Return occDoc

            Dim fullName As String = ""

            Try
                fullName = CStr(CallByName(descObj, "FullDocumentName", CallType.Get))
            Catch
                fullName = ""
            End Try

            If Not String.IsNullOrWhiteSpace(fullName) Then

                Try
                    occDoc = TryCast(ThisApplication.Documents.Open(fullName, False), INV.Document)
                Catch
                    occDoc = Nothing
                End Try

                If occDoc IsNot Nothing Then Return occDoc

            End If

        End If

    Catch
    End Try

    Try
        Dim fileDescObj As Object = CallByName(pickedOcc, "ReferencedFileDescriptor", CallType.Get)

        If fileDescObj IsNot Nothing Then

            Dim fileName As String = ""

            Try
                fileName = CStr(CallByName(fileDescObj, "FullFileName", CallType.Get))
            Catch
                fileName = ""
            End Try

            If Not String.IsNullOrWhiteSpace(fileName) Then

                Try
                    occDoc = TryCast(ThisApplication.Documents.Open(fileName, False), INV.Document)
                Catch
                    occDoc = Nothing
                End Try

                If occDoc IsNot Nothing Then Return occDoc

            End If

        End If

    Catch
    End Try

    Return Nothing

End Function

Private Sub ActionButtonClick(sender As Object, e As System.EventArgs)

    Dim btn As WF.Button = TryCast(sender, WF.Button)

    If btn Is Nothing Then Exit Sub

    Dim f As WF.Form = btn.FindForm()

    If f Is Nothing Then Exit Sub

    f.Tag = CStr(btn.Tag)
    f.Close()

End Sub

Private Function IsRecordingAction(actionName As String) As Boolean

    If actionName = "SUPPRESS_OCC" Then Return True
    If actionName = "UNSUPPRESS_OCC" Then Return True
    If actionName = "SUPPRESS_FEATURE" Then Return True
    If actionName = "UNSUPPRESS_FEATURE" Then Return True

    Return False

End Function

Private Function ConfirmClearPreviousRecordedStepsIfNeeded(recorderFile As String) As Boolean

    If Not IO.File.Exists(recorderFile) Then
        Return True
    End If

    Dim existingText As String = ""

    Try
        existingText = IO.File.ReadAllText(recorderFile)
    Catch
        existingText = ""
    End Try

    If String.IsNullOrWhiteSpace(existingText) Then
        Return True
    End If

    Dim result As WF.DialogResult = WF.MessageBox.Show("Previous recorded steps already exist." & vbCrLf & vbCrLf & _
                                                       "Do you want to clear them before recording this new step?" & vbCrLf & vbCrLf & _
                                                       "Yes = clear previous steps and continue" & vbCrLf & _
                                                       "No = keep previous steps and add this new step", _
                                                       "Internal CAD Tag", _
                                                       WF.MessageBoxButtons.YesNo, _
                                                       WF.MessageBoxIcon.Question)

    If result = WF.DialogResult.Yes Then

        Try
            IO.File.Delete(recorderFile)
        Catch ex As Exception
            WF.MessageBox.Show("Could not clear previous recorded steps." & vbCrLf & vbCrLf & ex.Message, "Internal CAD Tag")
            Return False
        End Try

    End If

    Return True

End Function

Private Function ResolveEffectiveTagForSelectedOccurrenceForSingleUnsuppress(pickedOcc As INV.ComponentOccurrence, tagNs As String, tagKey As String, dateKey As String, userKey As String, docTypeKey As String, proposedTag As String) As String

    If pickedOcc Is Nothing Then Return ""

    Dim occDoc As INV.Document = GetDocumentFromOccurrenceSafe(pickedOcc)

    If occDoc Is Nothing Then

        Try
            If pickedOcc.Suppressed Then
                pickedOcc.Unsuppress()
            End If
        Catch
        End Try

        occDoc = GetDocumentFromOccurrenceSafe(pickedOcc)

    End If

    If occDoc Is Nothing Then
        WF.MessageBox.Show("Could not read the selected occurrence document." & vbCrLf & vbCrLf & _
                           "This code will abort.", _
                           "Internal CAD Tag")
        Return ""
    End If

    Dim existingTag As String = GetTagValue(occDoc, tagNs, tagKey)

    If String.IsNullOrWhiteSpace(existingTag) Then

        If occDoc.DocumentType = INV.DocumentTypeEnum.kPartDocumentObject Then

            Dim p As INV.PartDocument = TryCast(occDoc, INV.PartDocument)

            If p IsNot Nothing Then
                existingTag = GetTagValue(p.ComponentDefinition, tagNs, tagKey)
            End If

        ElseIf occDoc.DocumentType = INV.DocumentTypeEnum.kAssemblyDocumentObject Then

            Dim a As INV.AssemblyDocument = TryCast(occDoc, INV.AssemblyDocument)

            If a IsNot Nothing Then
                existingTag = GetTagValue(a.ComponentDefinition, tagNs, tagKey)
            End If

        End If

    End If

    If Not String.IsNullOrWhiteSpace(existingTag) Then
        Return existingTag
    End If

    If String.IsNullOrWhiteSpace(proposedTag) Then
        WF.MessageBox.Show("The selected occurrence does not have a tag, and no new tag name was entered." & vbCrLf & vbCrLf & _
                           "This code will abort.", _
                           "Internal CAD Tag")
        Return ""
    End If

    Dim result As WF.DialogResult = WF.MessageBox.Show("The selected occurrence does not have an internal CAD tag." & vbCrLf & vbCrLf & _
                                                       "Selected occurrence:" & vbCrLf & _
                                                       pickedOcc.Name & vbCrLf & vbCrLf & _
                                                       "New tag to write:" & vbCrLf & _
                                                       proposedTag & vbCrLf & vbCrLf & _
                                                       "Do you want to write this tag to the selected occurrence document?", _
                                                       "Internal CAD Tag", _
                                                       WF.MessageBoxButtons.YesNo, _
                                                       WF.MessageBoxIcon.Warning)

    If result <> WF.DialogResult.Yes Then
        WF.MessageBox.Show("No tag was written." & vbCrLf & vbCrLf & _
                           "This code will abort because the selected occurrence has no tag.", _
                           "Internal CAD Tag")
        Return ""
    End If

    If occDoc.DocumentType = INV.DocumentTypeEnum.kPartDocumentObject Then

        Dim p As INV.PartDocument = TryCast(occDoc, INV.PartDocument)

        If p Is Nothing Then
            WF.MessageBox.Show("Could not write tag because the selected occurrence document could not be read as a part.", "Internal CAD Tag")
            Return ""
        End If

        WriteFullTag(p, p.ComponentDefinition, tagNs, tagKey, dateKey, userKey, docTypeKey, proposedTag, "Part")

        Try
            p.Save()
        Catch
        End Try

        Return proposedTag

    ElseIf occDoc.DocumentType = INV.DocumentTypeEnum.kAssemblyDocumentObject Then

        Dim a As INV.AssemblyDocument = TryCast(occDoc, INV.AssemblyDocument)

        If a Is Nothing Then
            WF.MessageBox.Show("Could not write tag because the selected occurrence document could not be read as an assembly.", "Internal CAD Tag")
            Return ""
        End If

        WriteFullTag(a, a.ComponentDefinition, tagNs, tagKey, dateKey, userKey, docTypeKey, proposedTag, "Assembly")

        Try
            a.Save()
        Catch
        End Try

        Return proposedTag

    End If

    WF.MessageBox.Show("Only part and assembly occurrence documents are supported.", "Internal CAD Tag")

    Return ""

End Function

Private Sub WriteFullTag(docObj As Object, defObj As Object, ns As String, tagKey As String, dateKey As String, userKey As String, docTypeKey As String, tagValue As String, docTypeValue As String)

    Dim nowText As String = DateTime.Now.ToString("yyyy-MM-dd HH:mm:ss")
    Dim userText As String = System.Environment.UserName

    WriteTagToObject(docObj, ns, tagKey, tagValue)
    WriteTagToObject(defObj, ns, tagKey, tagValue)

    WriteTagToObject(docObj, ns, dateKey, nowText)
    WriteTagToObject(defObj, ns, dateKey, nowText)

    WriteTagToObject(docObj, ns, userKey, userText)
    WriteTagToObject(defObj, ns, userKey, userText)

    WriteTagToObject(docObj, ns, docTypeKey, docTypeValue)
    WriteTagToObject(defObj, ns, docTypeKey, docTypeValue)

End Sub

Private Sub WriteTagToObject(o As Object, ns As String, key As String, val As String)

    On Error Resume Next

    Dim sets As INV.AttributeSets = Nothing
    sets = DirectCast(CallByName(o, "AttributeSets", CallType.Get), INV.AttributeSets)

    If Err.Number <> 0 OrElse sets Is Nothing Then
        Err.Clear()
        Exit Sub
    End If

    Dim aset As INV.AttributeSet = Nothing
    aset = sets.Item(ns)

    If Err.Number <> 0 OrElse aset Is Nothing Then
        Err.Clear()
        aset = sets.Add(ns)
    End If

    Dim at As INV.Attribute = Nothing
    at = aset.Item(key)

    If Err.Number = 0 AndAlso at IsNot Nothing Then
        at.Value = val
    Else
        Err.Clear()
        aset.Add(key, INV.ValueTypeEnum.kStringType, val)
    End If

    On Error GoTo 0

End Sub

Private Function HasTagValue(o As Object, ns As String, key As String, wantedValue As String) As Boolean

    Dim actualValue As String = GetTagValue(o, ns, key)

    If String.IsNullOrWhiteSpace(actualValue) Then
        HasTagValue = False
    Else
        HasTagValue = String.Compare(actualValue, wantedValue, True) = 0
    End If

End Function

Private Function GetTagValue(o As Object, ns As String, key As String) As String

    On Error Resume Next

    Dim sets As INV.AttributeSets = Nothing
    sets = DirectCast(CallByName(o, "AttributeSets", CallType.Get), INV.AttributeSets)

    If Err.Number <> 0 OrElse sets Is Nothing Then
        Err.Clear()
        GetTagValue = ""
        Exit Function
    End If

    Dim aset As INV.AttributeSet = Nothing
    aset = sets.Item(ns)

    If Err.Number <> 0 OrElse aset Is Nothing Then
        Err.Clear()
        GetTagValue = ""
        Exit Function
    End If

    Dim at As INV.Attribute = Nothing
    at = aset.Item(key)

    If Err.Number <> 0 OrElse at Is Nothing Then
        Err.Clear()
        GetTagValue = ""
        Exit Function
    End If

    GetTagValue = CStr(at.Value)

    On Error GoTo 0

End Function

Private Function FirstNonBlank(a As String, b As String) As String

    If Not String.IsNullOrWhiteSpace(a) Then
        FirstNonBlank = a
    Else
        FirstNonBlank = b
    End If

End Function

Private Sub SearchExactTag(topAsm As INV.AssemblyDocument, tagNs As String, tagKey As String, dateKey As String, userKey As String, docTypeKey As String, customTag As String)

    Dim foundText As String = ""
    Dim foundCount As Integer = 0
    Dim checkedPartCount As Integer = 0
    Dim checkedAsmCount As Integer = 0

    checkedAsmCount += 1

    If HasTagValue(topAsm, tagNs, tagKey, customTag) OrElse HasTagValue(topAsm.ComponentDefinition, tagNs, tagKey, customTag) Then

        foundCount += 1

        foundText &= "[TOP ASSEMBLY]" & vbCrLf
        foundText &= topAsm.DisplayName & vbCrLf
        foundText &= topAsm.FullFileName & vbCrLf
        foundText &= "Tag: " & customTag & vbCrLf & vbCrLf

    End If

    Dim d As INV.Document

    For Each d In topAsm.AllReferencedDocuments

        If d Is Nothing Then Continue For
        If String.IsNullOrEmpty(d.FullFileName) Then Continue For

        If d.DocumentType = INV.DocumentTypeEnum.kPartDocumentObject Then

            checkedPartCount += 1

            Dim p As INV.PartDocument = TryCast(d, INV.PartDocument)

            If p Is Nothing Then Continue For

            If HasTagValue(p, tagNs, tagKey, customTag) OrElse HasTagValue(p.ComponentDefinition, tagNs, tagKey, customTag) Then

                foundCount += 1

                foundText &= "[PART]" & vbCrLf
                foundText &= p.DisplayName & vbCrLf
                foundText &= p.FullFileName & vbCrLf
                foundText &= "Tag: " & customTag & vbCrLf & vbCrLf

            End If

        ElseIf d.DocumentType = INV.DocumentTypeEnum.kAssemblyDocumentObject Then

            checkedAsmCount += 1

            Dim subAsm As INV.AssemblyDocument = TryCast(d, INV.AssemblyDocument)

            If subAsm Is Nothing Then Continue For

            If HasTagValue(subAsm, tagNs, tagKey, customTag) OrElse HasTagValue(subAsm.ComponentDefinition, tagNs, tagKey, customTag) Then

                foundCount += 1

                foundText &= "[ASSEMBLY]" & vbCrLf
                foundText &= subAsm.DisplayName & vbCrLf
                foundText &= subAsm.FullFileName & vbCrLf
                foundText &= "Tag: " & customTag & vbCrLf & vbCrLf

            End If

        End If

    Next

    ShowResults("Exact Tag Search Results", checkedAsmCount, checkedPartCount, foundCount, customTag, foundText)

End Sub

Private Sub SearchAllTags(topAsm As INV.AssemblyDocument, tagNs As String, tagKey As String, dateKey As String, userKey As String, docTypeKey As String)

    Dim foundText As String = ""
    Dim foundCount As Integer = 0
    Dim checkedPartCount As Integer = 0
    Dim checkedAsmCount As Integer = 0

    checkedAsmCount += 1

    Dim topTag As String = GetTagValue(topAsm, tagNs, tagKey)

    If String.IsNullOrWhiteSpace(topTag) Then
        topTag = GetTagValue(topAsm.ComponentDefinition, tagNs, tagKey)
    End If

    If Not String.IsNullOrWhiteSpace(topTag) Then

        foundCount += 1

        foundText &= "[TOP ASSEMBLY]" & vbCrLf
        foundText &= topAsm.DisplayName & vbCrLf
        foundText &= topAsm.FullFileName & vbCrLf
        foundText &= "Tag: " & topTag & vbCrLf
        foundText &= "Tagged Date: " & FirstNonBlank(GetTagValue(topAsm, tagNs, dateKey), GetTagValue(topAsm.ComponentDefinition, tagNs, dateKey)) & vbCrLf
        foundText &= "Tagged By: " & FirstNonBlank(GetTagValue(topAsm, tagNs, userKey), GetTagValue(topAsm.ComponentDefinition, tagNs, userKey)) & vbCrLf
        foundText &= "Tagged Type: " & FirstNonBlank(GetTagValue(topAsm, tagNs, docTypeKey), GetTagValue(topAsm.ComponentDefinition, tagNs, docTypeKey)) & vbCrLf & vbCrLf

    End If

    Dim d As INV.Document

    For Each d In topAsm.AllReferencedDocuments

        If d Is Nothing Then Continue For
        If String.IsNullOrEmpty(d.FullFileName) Then Continue For

        If d.DocumentType = INV.DocumentTypeEnum.kPartDocumentObject Then

            checkedPartCount += 1

            Dim p As INV.PartDocument = TryCast(d, INV.PartDocument)

            If p Is Nothing Then Continue For

            Dim partTag As String = GetTagValue(p, tagNs, tagKey)

            If String.IsNullOrWhiteSpace(partTag) Then
                partTag = GetTagValue(p.ComponentDefinition, tagNs, tagKey)
            End If

            If Not String.IsNullOrWhiteSpace(partTag) Then

                foundCount += 1

                foundText &= "[PART]" & vbCrLf
                foundText &= p.DisplayName & vbCrLf
                foundText &= p.FullFileName & vbCrLf
                foundText &= "Tag: " & partTag & vbCrLf
                foundText &= "Tagged Date: " & FirstNonBlank(GetTagValue(p, tagNs, dateKey), GetTagValue(p.ComponentDefinition, tagNs, dateKey)) & vbCrLf
                foundText &= "Tagged By: " & FirstNonBlank(GetTagValue(p, tagNs, userKey), GetTagValue(p.ComponentDefinition, tagNs, userKey)) & vbCrLf
                foundText &= "Tagged Type: " & FirstNonBlank(GetTagValue(p, tagNs, docTypeKey), GetTagValue(p.ComponentDefinition, tagNs, docTypeKey)) & vbCrLf & vbCrLf

            End If

        ElseIf d.DocumentType = INV.DocumentTypeEnum.kAssemblyDocumentObject Then

            checkedAsmCount += 1

            Dim subAsm As INV.AssemblyDocument = TryCast(d, INV.AssemblyDocument)

            If subAsm Is Nothing Then Continue For

            Dim asmTag As String = GetTagValue(subAsm, tagNs, tagKey)

            If String.IsNullOrWhiteSpace(asmTag) Then
                asmTag = GetTagValue(subAsm.ComponentDefinition, tagNs, tagKey)
            End If

            If Not String.IsNullOrWhiteSpace(asmTag) Then

                foundCount += 1

                foundText &= "[ASSEMBLY]" & vbCrLf
                foundText &= subAsm.DisplayName & vbCrLf
                foundText &= subAsm.FullFileName & vbCrLf
                foundText &= "Tag: " & asmTag & vbCrLf
                foundText &= "Tagged Date: " & FirstNonBlank(GetTagValue(subAsm, tagNs, dateKey), GetTagValue(subAsm.ComponentDefinition, tagNs, dateKey)) & vbCrLf
                foundText &= "Tagged By: " & FirstNonBlank(GetTagValue(subAsm, tagNs, userKey), GetTagValue(subAsm.ComponentDefinition, tagNs, userKey)) & vbCrLf
                foundText &= "Tagged Type: " & FirstNonBlank(GetTagValue(subAsm, tagNs, docTypeKey), GetTagValue(subAsm.ComponentDefinition, tagNs, docTypeKey)) & vbCrLf & vbCrLf

            End If

        End If

    Next

    ShowResults("All Tag Search Results", checkedAsmCount, checkedPartCount, foundCount, "ALL INTERNAL CAD TAGS", foundText)

End Sub

Private Sub ShowResults(title As String, checkedAsmCount As Integer, checkedPartCount As Integer, foundCount As Integer, searchedTag As String, foundText As String)

    If foundCount = 0 Then

        WF.MessageBox.Show("Checked assemblies: " & checkedAsmCount.ToString() & vbCrLf & _
                           "Checked parts: " & checkedPartCount.ToString() & vbCrLf & _
                           "Matching tagged files: 0" & vbCrLf & _
                           "Search: " & searchedTag, _
                           title)

    Else

        Dim resultForm As New WF.Form()
        resultForm.Text = title
        resultForm.StartPosition = WF.FormStartPosition.CenterParent
        resultForm.Width = 860
        resultForm.Height = 540

        Dim resultBox As New WF.TextBox()
        resultBox.Multiline = True
        resultBox.ReadOnly = True
        resultBox.ScrollBars = WF.ScrollBars.Both
        resultBox.WordWrap = False
        resultBox.Dock = WF.DockStyle.Fill
        resultBox.Text = "Checked assemblies: " & checkedAsmCount.ToString() & vbCrLf & _
                         "Checked parts: " & checkedPartCount.ToString() & vbCrLf & _
                         "Matching tagged files: " & foundCount.ToString() & vbCrLf & _
                         "Search: " & searchedTag & vbCrLf & vbCrLf & _
                         foundText

        resultForm.Controls.Add(resultBox)
        resultForm.ShowDialog()

    End If

End Sub

Private Function SuppressOccurrencesByTag(occs As INV.ComponentOccurrences, tagNs As String, tagKey As String, wantedTag As String) As Integer

    Dim targets As New System.Collections.ArrayList()

    CollectOccurrencesByTag(occs, tagNs, tagKey, wantedTag, targets)

    Return ApplyQueuedMatchedTaggedOccurrencesActive(targets, False)

End Function

Private Function SetOccurrenceSuppressedOrExcluded(occ As INV.ComponentOccurrence, suppressState As Boolean) As Boolean

    If occ Is Nothing Then Return False

    Dim wantedActive As Boolean = Not suppressState

    Try
        CallByName(occ, "Visible", CallType.Let, wantedActive)
    Catch
    End Try

    Try
        If suppressState Then
            If occ.Suppressed Then Return True
        Else
            If Not occ.Suppressed Then Return True
        End If
    Catch
    End Try

    Try
        If suppressState Then
            If Not occ.Suppressed Then
                occ.Suppress()
            End If
        Else
            If occ.Suppressed Then
                occ.Unsuppress()
            End If
        End If
    Catch
    End Try

    Try
        If suppressState Then
            Return occ.Suppressed
        Else
            Return Not occ.Suppressed
        End If
    Catch
    End Try

    Return False

End Function

Private Function IsOccurrenceExcludedInActiveIAssemblyRow(occ As INV.ComponentOccurrence) As Boolean

    If occ Is Nothing Then Return False

    Dim app As INV.Application = ThisApplication
    Dim asmDoc As INV.AssemblyDocument = TryCast(app.ActiveDocument, INV.AssemblyDocument)

    If asmDoc Is Nothing Then Return False

    Dim asmDef As INV.AssemblyComponentDefinition = asmDoc.ComponentDefinition
    Dim factoryObj As Object = Nothing
    Dim rowObj As Object = Nothing

    Try
        factoryObj = CallByName(asmDef, "iAssemblyFactory", CallType.Get)
    Catch
        factoryObj = Nothing
    End Try

    If factoryObj Is Nothing Then

        Try
            Return occ.Suppressed
        Catch
            Return False
        End Try

    End If

    Try
        rowObj = CallByName(factoryObj, "DefaultRow", CallType.Get)
    Catch
        rowObj = Nothing
    End Try

    If rowObj Is Nothing Then Return False

    Try
        Return CBool(CallByName(rowObj, "IsExcluded", CallType.Method, occ))
    Catch
        Return False
    End Try

End Function

Private Function SetMatchedTaggedOccurrenceActive(occ As INV.ComponentOccurrence, activeState As Boolean) As Boolean

    If occ Is Nothing Then Return False

    Dim app As INV.Application = ThisApplication
    Dim asmDoc As INV.AssemblyDocument = TryCast(app.ActiveDocument, INV.AssemblyDocument)

    If asmDoc Is Nothing Then Return False

    Dim asmDef As INV.AssemblyComponentDefinition = asmDoc.ComponentDefinition
    Dim isIAssemblyFactory As Boolean = False

    Try
        isIAssemblyFactory = asmDef.IsiAssemblyFactory
    Catch
        isIAssemblyFactory = False
    End Try

    If Not isIAssemblyFactory Then

        Try
            If activeState Then
                If occ.Suppressed Then
                    occ.Unsuppress()
                End If
            Else
                If Not occ.Suppressed Then
                    occ.Suppress()
                End If
            End If
        Catch
        End Try

        Try
            If activeState Then
                Return Not occ.Suppressed
            Else
                Return occ.Suppressed
            End If
        Catch
        End Try

        Return False

    End If

    Dim beforeExcluded As Boolean = IsOccurrenceExcludedInActiveIAssemblyRow(occ)
    Dim wantedExcluded As Boolean = Not activeState

    If beforeExcluded = wantedExcluded Then
        Return True
    End If

    Try
        asmDoc.SelectSet.Clear()
        asmDoc.SelectSet.Select(occ)

        app.CommandManager.ControlDefinitions.Item("ExcludeCtxCmd").Execute()

        WF.Application.DoEvents()

        Try
            asmDoc.Update()
        Catch
        End Try

        Try
            asmDoc.SelectSet.Clear()
        Catch
        End Try

    Catch
        Try
            asmDoc.SelectSet.Clear()
        Catch
        End Try

        Return False
    End Try

    Dim afterExcluded As Boolean = IsOccurrenceExcludedInActiveIAssemblyRow(occ)

    If afterExcluded = wantedExcluded Then
        Try
            asmDoc.Save()
        Catch
        End Try

        Return True
    End If

    Return False

End Function

Private Function SetIAssemblyOccurrenceIncludedByRowCell(occ As INV.ComponentOccurrence) As Boolean

    Return SetIAssemblyOccurrenceExcludedStateByRowCell(occ, False)

End Function

Private Function SetIAssemblyOccurrenceExcludedByRowCell(occ As INV.ComponentOccurrence) As Boolean

    Return SetIAssemblyOccurrenceExcludedStateByRowCell(occ, True)

End Function

Private Function SetIAssemblyOccurrenceExcludedStateByRowCell(occ As INV.ComponentOccurrence, wantedExcluded As Boolean) As Boolean

    If occ Is Nothing Then Return False

    Dim app As INV.Application = ThisApplication
    Dim asmDoc As INV.AssemblyDocument = TryCast(app.ActiveDocument, INV.AssemblyDocument)

    If asmDoc Is Nothing Then Return False

    Dim asmDef As INV.AssemblyComponentDefinition = asmDoc.ComponentDefinition
    Dim factoryObj As Object = Nothing
    Dim rowObj As Object = Nothing
    Dim columnsObj As Object = Nothing

    Try
        factoryObj = CallByName(asmDef, "iAssemblyFactory", CallType.Get)
    Catch
        factoryObj = Nothing
    End Try

    If factoryObj Is Nothing Then Return False

    Try
        rowObj = CallByName(factoryObj, "DefaultRow", CallType.Get)
    Catch
        rowObj = Nothing
    End Try

    If rowObj Is Nothing Then Return False

    Try
        columnsObj = CallByName(factoryObj, "TableColumns", CallType.Get)
    Catch
        columnsObj = Nothing
    End Try

    If columnsObj Is Nothing Then Return False

    Dim targetHeading As String = occ.Name & ":Include/Exclude"
    Dim wantedValue As String = ""

    If wantedExcluded Then
        wantedValue = "Exclude"
    Else
        wantedValue = "Include"
    End If

    Dim colCount As Integer = 0

    Try
        colCount = CInt(CallByName(columnsObj, "Count", CallType.Get))
    Catch
        colCount = 0
    End Try

    If colCount <= 0 Then Return False

    Dim i As Integer

    For i = 1 To colCount

        Dim colObj As Object = Nothing
        Dim cellObj As Object = Nothing
        Dim headingText As String = ""

        Try
            colObj = CallByName(columnsObj, "Item", CallType.Get, i)
        Catch
            colObj = Nothing
        End Try

        If colObj Is Nothing Then Continue For

        Try
            headingText = System.Convert.ToString(CallByName(colObj, "Heading", CallType.Get))
        Catch
            headingText = ""
        End Try

        If String.Compare(headingText, targetHeading, True) <> 0 Then Continue For

        Try
            cellObj = CallByName(rowObj, "Item", CallType.Get, i)
        Catch
            cellObj = Nothing
        End Try

        If cellObj Is Nothing Then Return False

        Try
            CallByName(cellObj, "Value", CallType.Set, wantedValue)
        Catch
            Return False
        End Try

        Try
            asmDoc.Update()
        Catch
        End Try

        Dim afterExcluded As Boolean = False

        Try
            afterExcluded = CBool(CallByName(rowObj, "IsExcluded", CallType.Method, occ))
        Catch
            afterExcluded = False
        End Try

        If afterExcluded = wantedExcluded Then
            Return True
        End If

        Return False

    Next

    WF.MessageBox.Show("Could not find the iAssembly Include/Exclude column for this occurrence." & vbCrLf & vbCrLf & _
                       "Occurrence: " & occ.Name & vbCrLf & _
                       "Expected heading: " & targetHeading, _
                       "Internal CAD Tag")

    Return False

End Function

Private Function UnsuppressOccurrencesByTag(occs As INV.ComponentOccurrences, tagNs As String, tagKey As String, wantedTag As String) As Integer

    Dim count As Integer = 0
    Dim occ As INV.ComponentOccurrence

    For Each occ In occs

        On Error Resume Next

        If occ.Suppressed Then
            occ.Unsuppress()
        End If

        Dim occDoc As INV.Document = Nothing
        occDoc = occ.Definition.Document

        If Err.Number = 0 AndAlso occDoc IsNot Nothing Then

            If HasTagValue(occDoc, tagNs, tagKey, wantedTag) Then
                count += 1
            ElseIf occDoc.DocumentType = INV.DocumentTypeEnum.kAssemblyDocumentObject Then
                Dim subDef As INV.AssemblyComponentDefinition = TryCast(occ.Definition, INV.AssemblyComponentDefinition)
                If subDef IsNot Nothing Then
                    count += UnsuppressOccurrencesByTag(subDef.Occurrences, tagNs, tagKey, wantedTag)
                End If
            Else
                occ.Suppress()
            End If

        End If

        Err.Clear()
        On Error GoTo 0

    Next

    UnsuppressOccurrencesByTag = count

End Function

Private Sub AppendRecorderStep(recorderFile As String, stepText As String)

    IO.File.AppendAllText(recorderFile, stepText & vbCrLf)

    Try
        ShowGeneratedCodeFromRecorder(recorderFile, "INTERNAL_CAD_TAG", "TagName")
    Catch ex As Exception
        WF.MessageBox.Show("The step was recorded, but the generated code window could not be opened." & vbCrLf & vbCrLf & _
                           ex.Message, _
                           "Internal CAD Tag")
    End Try

End Sub

Private Sub ShowGeneratedCodeFromRecorder(recorderFile As String, tagNs As String, tagKey As String)

    If Not IO.File.Exists(recorderFile) Then
        WF.MessageBox.Show("No recorded steps found.", "Generated iLogic Code")
        Exit Sub
    End If

    Dim lines() As String = IO.File.ReadAllLines(recorderFile)

    If lines.Length = 0 Then
        WF.MessageBox.Show("No recorded steps found.", "Generated iLogic Code")
        Exit Sub
    End If

    Dim codeText As String = BuildGeneratedCode(lines, tagNs, tagKey)

    Dim resultForm As New WF.Form()
    resultForm.Text = "Generated iLogic Code"
    resultForm.StartPosition = WF.FormStartPosition.CenterParent
    resultForm.Width = 1050
    resultForm.Height = 760

    Dim resultBox As New WF.TextBox()
    resultBox.Multiline = True
    resultBox.ReadOnly = False
    resultBox.ScrollBars = WF.ScrollBars.Both
    resultBox.WordWrap = False
    resultBox.Dock = WF.DockStyle.Fill
    resultBox.Font = New SD.Font("Consolas", 9.0!)
    resultBox.Text = codeText

    resultForm.Controls.Add(resultBox)
    resultForm.ShowDialog()

End Sub

Private Function BuildGeneratedCode(lines() As String, tagNs As String, tagKey As String) As String

    Dim s As String = ""

    s &= "AddReference ""System.Windows.Forms.dll""" & vbCrLf
    s &= "Imports INV = Inventor" & vbCrLf
    s &= "Imports WF = System.Windows.Forms" & vbCrLf
    s &= "Imports IO = System.IO" & vbCrLf
    s &= vbCrLf
    s &= "Sub Main()" & vbCrLf
    s &= "    Const TAG_NS As String = """ & tagNs & """" & vbCrLf
    s &= "    Const TAG_KEY As String = """ & tagKey & """" & vbCrLf
    s &= vbCrLf
    s &= "    Dim app As INV.Application = ThisApplication" & vbCrLf
    s &= "    Dim activeDoc As INV.Document = app.ActiveDocument" & vbCrLf
    s &= "    Dim asm As INV.AssemblyDocument = TryCast(activeDoc, INV.AssemblyDocument)" & vbCrLf
    s &= "    Dim part As INV.PartDocument = TryCast(activeDoc, INV.PartDocument)" & vbCrLf
    s &= "    Dim txn As INV.Transaction = Nothing" & vbCrLf
    s &= vbCrLf
    s &= "    Try" & vbCrLf
    s &= "        If activeDoc IsNot Nothing Then" & vbCrLf
    s &= "            txn = app.TransactionManager.StartTransaction(activeDoc, ""Internal CAD Tag Replay"")" & vbCrLf
    s &= "        End If" & vbCrLf
    s &= vbCrLf

    Dim i As Integer

    For i = 0 To lines.Length - 1

        Dim lineText As String = lines(i).Trim()

        If String.IsNullOrWhiteSpace(lineText) Then Continue For

        Dim parts() As String = lineText.Split("|"c)

        If parts.Length = 0 Then Continue For

        Dim actionName As String = parts(0)

        If actionName = "SUPPRESS_OCC" AndAlso parts.Length >= 2 Then

            s &= "        If asm Is Nothing Then" & vbCrLf
            s &= "            WF.MessageBox.Show(""Open an assembly first for occurrence suppression."")" & vbCrLf
            s &= "            Exit Sub" & vbCrLf
            s &= "        End If" & vbCrLf
            s &= "        SuppressOccurrencesByTag(asm.ComponentDefinition.Occurrences, TAG_NS, TAG_KEY, """ & EscapeForVb(parts(1)) & """)" & vbCrLf
            s &= vbCrLf

        ElseIf actionName = "UNSUPPRESS_OCC" AndAlso parts.Length >= 2 Then

            s &= "        If asm Is Nothing Then" & vbCrLf
            s &= "            WF.MessageBox.Show(""Open an assembly first for occurrence unsuppression."")" & vbCrLf
            s &= "            Exit Sub" & vbCrLf
            s &= "        End If" & vbCrLf
            s &= "        UnsuppressOccurrencesByTagSafe(asm.ComponentDefinition.Occurrences, TAG_NS, TAG_KEY, """ & EscapeForVb(parts(1)) & """)" & vbCrLf
            s &= vbCrLf

        ElseIf actionName = "UNSUPPRESS_SELECTED_OCC" AndAlso parts.Length >= 3 Then

            s &= "        If asm Is Nothing Then" & vbCrLf
            s &= "            WF.MessageBox.Show(""Open an assembly first for selected occurrence unsuppression."")" & vbCrLf
            s &= "            Exit Sub" & vbCrLf
            s &= "        End If" & vbCrLf
            s &= "        UnsuppressOccurrenceByNameAndTag(asm.ComponentDefinition.Occurrences, TAG_NS, TAG_KEY, """ & EscapeForVb(parts(1)) & """, """ & EscapeForVb(parts(2)) & """)" & vbCrLf
            s &= vbCrLf

        ElseIf actionName = "SUPPRESS_FEATURE" AndAlso parts.Length >= 3 Then

            s &= "        If asm IsNot Nothing Then" & vbCrLf
            s &= "            SetFeatureActiveByTag(asm, TAG_NS, TAG_KEY, """ & EscapeForVb(parts(1)) & """, """ & EscapeForVb(parts(2)) & """, False)" & vbCrLf
            s &= "        ElseIf part IsNot Nothing Then" & vbCrLf
            s &= "            If HasTagValue(part, TAG_NS, TAG_KEY, """ & EscapeForVb(parts(1)) & """) OrElse HasTagValue(part.ComponentDefinition, TAG_NS, TAG_KEY, """ & EscapeForVb(parts(1)) & """) Then" & vbCrLf
            s &= "                Feature.IsActive(""" & EscapeForVb(parts(2)) & """) = False" & vbCrLf
            s &= "            End If" & vbCrLf
            s &= "        End If" & vbCrLf
            s &= vbCrLf

        ElseIf actionName = "UNSUPPRESS_FEATURE" AndAlso parts.Length >= 3 Then

            s &= "        If asm IsNot Nothing Then" & vbCrLf
            s &= "            SetFeatureActiveByTag(asm, TAG_NS, TAG_KEY, """ & EscapeForVb(parts(1)) & """, """ & EscapeForVb(parts(2)) & """, True)" & vbCrLf
            s &= "        ElseIf part IsNot Nothing Then" & vbCrLf
            s &= "            If HasTagValue(part, TAG_NS, TAG_KEY, """ & EscapeForVb(parts(1)) & """) OrElse HasTagValue(part.ComponentDefinition, TAG_NS, TAG_KEY, """ & EscapeForVb(parts(1)) & """) Then" & vbCrLf
            s &= "                Feature.IsActive(""" & EscapeForVb(parts(2)) & """) = True" & vbCrLf
            s &= "            End If" & vbCrLf
            s &= "        End If" & vbCrLf
            s &= vbCrLf

        End If

    Next

    s &= "        If txn IsNot Nothing Then" & vbCrLf
    s &= "            txn.End()" & vbCrLf
    s &= "            txn = Nothing" & vbCrLf
    s &= "        End If" & vbCrLf
    s &= vbCrLf
    s &= "        InventorVb.DocumentUpdate(True)" & vbCrLf
    s &= vbCrLf
    s &= "    Catch ex As Exception" & vbCrLf
    s &= "        If txn IsNot Nothing Then" & vbCrLf
    s &= "            Try" & vbCrLf
    s &= "                txn.Abort()" & vbCrLf
    s &= "            Catch" & vbCrLf
    s &= "            End Try" & vbCrLf
    s &= "        End If" & vbCrLf
    s &= vbCrLf
    s &= "        WF.MessageBox.Show(ex.Message, ""Internal CAD Tag Replay Error"")" & vbCrLf
    s &= "        Exit Sub" & vbCrLf
    s &= "    End Try" & vbCrLf
    s &= vbCrLf
    s &= "End Sub" & vbCrLf
    s &= vbCrLf

    s &= GetGeneratedHelperCode()

    BuildGeneratedCode = s

End Function

Private Function EscapeForVb(value As String) As String

    EscapeForVb = value.Replace("""", """""")

End Function

Private Function GetGeneratedHelperCode() As String

    Dim s As String = ""

    s &= "Private Function HasTagValue(o As Object, ns As String, key As String, wantedValue As String) As Boolean" & vbCrLf
    s &= vbCrLf
    s &= "    Dim actualValue As String = GetTagValue(o, ns, key)" & vbCrLf
    s &= vbCrLf
    s &= "    If String.IsNullOrWhiteSpace(actualValue) Then" & vbCrLf
    s &= "        Return False" & vbCrLf
    s &= "    End If" & vbCrLf
    s &= vbCrLf
    s &= "    Return String.Compare(actualValue, wantedValue, True) = 0" & vbCrLf
    s &= vbCrLf
    s &= "End Function" & vbCrLf
    s &= vbCrLf

    s &= "Private Function GetTagValue(o As Object, ns As String, key As String) As String" & vbCrLf
    s &= vbCrLf
    s &= "    On Error Resume Next" & vbCrLf
    s &= vbCrLf
    s &= "    Dim sets As INV.AttributeSets = Nothing" & vbCrLf
    s &= "    sets = DirectCast(CallByName(o, ""AttributeSets"", CallType.Get), INV.AttributeSets)" & vbCrLf
    s &= vbCrLf
    s &= "    If Err.Number <> 0 OrElse sets Is Nothing Then" & vbCrLf
    s &= "        Err.Clear()" & vbCrLf
    s &= "        Return """"" & vbCrLf
    s &= "    End If" & vbCrLf
    s &= vbCrLf
    s &= "    Dim aset As INV.AttributeSet = Nothing" & vbCrLf
    s &= "    aset = sets.Item(ns)" & vbCrLf
    s &= vbCrLf
    s &= "    If Err.Number <> 0 OrElse aset Is Nothing Then" & vbCrLf
    s &= "        Err.Clear()" & vbCrLf
    s &= "        Return """"" & vbCrLf
    s &= "    End If" & vbCrLf
    s &= vbCrLf
    s &= "    Dim at As INV.Attribute = Nothing" & vbCrLf
    s &= "    at = aset.Item(key)" & vbCrLf
    s &= vbCrLf
    s &= "    If Err.Number <> 0 OrElse at Is Nothing Then" & vbCrLf
    s &= "        Err.Clear()" & vbCrLf
    s &= "        Return """"" & vbCrLf
    s &= "    End If" & vbCrLf
    s &= vbCrLf
    s &= "    Dim v As String = CStr(at.Value)" & vbCrLf
    s &= vbCrLf
    s &= "    On Error GoTo 0" & vbCrLf
    s &= vbCrLf
    s &= "    Return v" & vbCrLf
    s &= vbCrLf
    s &= "End Function" & vbCrLf
    s &= vbCrLf

    s &= "Private Function HasComponentDefinitionTagValue(doc As INV.Document, ns As String, key As String, wantedValue As String) As Boolean" & vbCrLf
    s &= vbCrLf
    s &= "    If doc Is Nothing Then Return False" & vbCrLf
    s &= vbCrLf
    s &= "    If doc.DocumentType = INV.DocumentTypeEnum.kPartDocumentObject Then" & vbCrLf
    s &= vbCrLf
    s &= "        Dim p As INV.PartDocument = TryCast(doc, INV.PartDocument)" & vbCrLf
    s &= vbCrLf
    s &= "        If p IsNot Nothing Then" & vbCrLf
    s &= "            Return HasTagValue(p.ComponentDefinition, ns, key, wantedValue)" & vbCrLf
    s &= "        End If" & vbCrLf
    s &= vbCrLf
    s &= "    ElseIf doc.DocumentType = INV.DocumentTypeEnum.kAssemblyDocumentObject Then" & vbCrLf
    s &= vbCrLf
    s &= "        Dim a As INV.AssemblyDocument = TryCast(doc, INV.AssemblyDocument)" & vbCrLf
    s &= vbCrLf
    s &= "        If a IsNot Nothing Then" & vbCrLf
    s &= "            Return HasTagValue(a.ComponentDefinition, ns, key, wantedValue)" & vbCrLf
    s &= "        End If" & vbCrLf
    s &= vbCrLf
    s &= "    End If" & vbCrLf
    s &= vbCrLf
    s &= "    Return False" & vbCrLf
    s &= vbCrLf
    s &= "End Function" & vbCrLf
    s &= vbCrLf

    s &= "Private Function GetOccurrenceDocumentSafe(occ As INV.ComponentOccurrence) As INV.Document" & vbCrLf
    s &= vbCrLf
    s &= "    If occ Is Nothing Then Return Nothing" & vbCrLf
    s &= vbCrLf
    s &= "    Dim occDoc As INV.Document = Nothing" & vbCrLf
    s &= vbCrLf
    s &= "    Try" & vbCrLf
    s &= "        occDoc = occ.Definition.Document" & vbCrLf
    s &= "    Catch" & vbCrLf
    s &= "        occDoc = Nothing" & vbCrLf
    s &= "    End Try" & vbCrLf
    s &= vbCrLf
    s &= "    If occDoc IsNot Nothing Then Return occDoc" & vbCrLf
    s &= vbCrLf
    s &= "    Try" & vbCrLf
    s &= "        Dim descObj As Object = CallByName(occ, ""ReferencedDocumentDescriptor"", CallType.Get)" & vbCrLf
    s &= vbCrLf
    s &= "        If descObj IsNot Nothing Then" & vbCrLf
    s &= vbCrLf
    s &= "            Try" & vbCrLf
    s &= "                occDoc = TryCast(CallByName(descObj, ""ReferencedDocument"", CallType.Get), INV.Document)" & vbCrLf
    s &= "            Catch" & vbCrLf
    s &= "                occDoc = Nothing" & vbCrLf
    s &= "            End Try" & vbCrLf
    s &= vbCrLf
    s &= "            If occDoc IsNot Nothing Then Return occDoc" & vbCrLf
    s &= vbCrLf
    s &= "            Dim fullName As String = """"" & vbCrLf
    s &= vbCrLf
    s &= "            Try" & vbCrLf
    s &= "                fullName = CStr(CallByName(descObj, ""FullDocumentName"", CallType.Get))" & vbCrLf
    s &= "            Catch" & vbCrLf
    s &= "                fullName = """"" & vbCrLf
    s &= "            End Try" & vbCrLf
    s &= vbCrLf
    s &= "            If Not String.IsNullOrWhiteSpace(fullName) Then" & vbCrLf
    s &= vbCrLf
    s &= "                Try" & vbCrLf
    s &= "                    occDoc = TryCast(ThisApplication.Documents.Open(fullName, False), INV.Document)" & vbCrLf
    s &= "                Catch" & vbCrLf
    s &= "                    occDoc = Nothing" & vbCrLf
    s &= "                End Try" & vbCrLf
    s &= vbCrLf
    s &= "                If occDoc IsNot Nothing Then Return occDoc" & vbCrLf
    s &= vbCrLf
    s &= "            End If" & vbCrLf
    s &= vbCrLf
    s &= "        End If" & vbCrLf
    s &= vbCrLf
    s &= "    Catch" & vbCrLf
    s &= "    End Try" & vbCrLf
    s &= vbCrLf
    s &= "    Try" & vbCrLf
    s &= "        Dim fileDescObj As Object = CallByName(occ, ""ReferencedFileDescriptor"", CallType.Get)" & vbCrLf
    s &= vbCrLf
    s &= "        If fileDescObj IsNot Nothing Then" & vbCrLf
    s &= vbCrLf
    s &= "            Dim fileName As String = """"" & vbCrLf
    s &= vbCrLf
    s &= "            Try" & vbCrLf
    s &= "                fileName = CStr(CallByName(fileDescObj, ""FullFileName"", CallType.Get))" & vbCrLf
    s &= "            Catch" & vbCrLf
    s &= "                fileName = """"" & vbCrLf
    s &= "            End Try" & vbCrLf
    s &= vbCrLf
    s &= "            If Not String.IsNullOrWhiteSpace(fileName) Then" & vbCrLf
    s &= vbCrLf
    s &= "                Try" & vbCrLf
    s &= "                    occDoc = TryCast(ThisApplication.Documents.Open(fileName, False), INV.Document)" & vbCrLf
    s &= "                Catch" & vbCrLf
    s &= "                    occDoc = Nothing" & vbCrLf
    s &= "                End Try" & vbCrLf
    s &= vbCrLf
    s &= "                If occDoc IsNot Nothing Then Return occDoc" & vbCrLf
    s &= vbCrLf
    s &= "            End If" & vbCrLf
    s &= vbCrLf
    s &= "        End If" & vbCrLf
    s &= vbCrLf
    s &= "    Catch" & vbCrLf
    s &= "    End Try" & vbCrLf
    s &= vbCrLf
    s &= "    Return Nothing" & vbCrLf
    s &= vbCrLf
    s &= "End Function" & vbCrLf
    s &= vbCrLf

    s &= "Private Function SuppressOccurrencesByTag(occs As INV.ComponentOccurrences, tagNs As String, tagKey As String, wantedTag As String) As Integer" & vbCrLf
    s &= vbCrLf
    s &= "    Dim targets As New System.Collections.ArrayList()" & vbCrLf
    s &= vbCrLf
    s &= "    CollectOccurrencesByTag(occs, tagNs, tagKey, wantedTag, targets)" & vbCrLf
    s &= vbCrLf
    s &= "    Return ApplyQueuedMatchedTaggedOccurrencesActive(targets, False)" & vbCrLf
    s &= vbCrLf
    s &= "End Function" & vbCrLf
    s &= vbCrLf

    s &= "Private Function UnsuppressOccurrencesByTagSafe(occs As INV.ComponentOccurrences, tagNs As String, tagKey As String, wantedTag As String) As Integer" & vbCrLf
    s &= vbCrLf
    s &= "    Dim targets As New System.Collections.ArrayList()" & vbCrLf
    s &= vbCrLf
    s &= "    CollectOccurrencesByTag(occs, tagNs, tagKey, wantedTag, targets)" & vbCrLf
    s &= vbCrLf
    s &= "    Return ApplyQueuedMatchedTaggedOccurrencesActive(targets, True)" & vbCrLf
    s &= vbCrLf
    s &= "End Function" & vbCrLf
    s &= vbCrLf

    s &= "Private Sub CollectOccurrencesByTag(occs As INV.ComponentOccurrences, tagNs As String, tagKey As String, wantedTag As String, targets As System.Collections.ArrayList)" & vbCrLf
    s &= vbCrLf
    s &= "    If occs Is Nothing Then Exit Sub" & vbCrLf
    s &= "    If targets Is Nothing Then Exit Sub" & vbCrLf
    s &= vbCrLf
    s &= "    Dim occ As INV.ComponentOccurrence" & vbCrLf
    s &= vbCrLf
    s &= "    For Each occ In occs" & vbCrLf
    s &= vbCrLf
    s &= "        Dim occDoc As INV.Document = GetOccurrenceDocumentSafe(occ)" & vbCrLf
    s &= vbCrLf
    s &= "        If occDoc IsNot Nothing Then" & vbCrLf
    s &= vbCrLf
    s &= "            If HasTagValue(occDoc, tagNs, tagKey, wantedTag) OrElse HasComponentDefinitionTagValue(occDoc, tagNs, tagKey, wantedTag) Then" & vbCrLf
    s &= vbCrLf
    s &= "                targets.Add(occ)" & vbCrLf
    s &= vbCrLf
    s &= "            ElseIf occDoc.DocumentType = INV.DocumentTypeEnum.kAssemblyDocumentObject Then" & vbCrLf
    s &= vbCrLf
    s &= "                Dim subDef As INV.AssemblyComponentDefinition = Nothing" & vbCrLf
    s &= vbCrLf
    s &= "                Try" & vbCrLf
    s &= "                    subDef = TryCast(occ.Definition, INV.AssemblyComponentDefinition)" & vbCrLf
    s &= "                Catch" & vbCrLf
    s &= "                    subDef = Nothing" & vbCrLf
    s &= "                End Try" & vbCrLf
    s &= vbCrLf
    s &= "                If subDef IsNot Nothing Then" & vbCrLf
    s &= "                    CollectOccurrencesByTag(subDef.Occurrences, tagNs, tagKey, wantedTag, targets)" & vbCrLf
    s &= "                End If" & vbCrLf
    s &= vbCrLf
    s &= "            End If" & vbCrLf
    s &= vbCrLf
    s &= "        End If" & vbCrLf
    s &= vbCrLf
    s &= "    Next" & vbCrLf
    s &= vbCrLf
    s &= "End Sub" & vbCrLf
    s &= vbCrLf

    s &= "Private Function ApplyQueuedMatchedTaggedOccurrencesActive(targets As System.Collections.ArrayList, activeState As Boolean) As Integer" & vbCrLf
    s &= vbCrLf
    s &= "    If targets Is Nothing Then Return 0" & vbCrLf
    s &= "    If targets.Count = 0 Then Return 0" & vbCrLf
    s &= vbCrLf
    s &= "    Dim app As INV.Application = ThisApplication" & vbCrLf
    s &= "    Dim asmDoc As INV.AssemblyDocument = TryCast(app.ActiveDocument, INV.AssemblyDocument)" & vbCrLf
    s &= vbCrLf
    s &= "    If asmDoc Is Nothing Then Return 0" & vbCrLf
    s &= vbCrLf
    s &= "    Dim asmDef As INV.AssemblyComponentDefinition = asmDoc.ComponentDefinition" & vbCrLf
    s &= "    Dim isIAssemblyFactory As Boolean = False" & vbCrLf
    s &= vbCrLf
    s &= "    Try" & vbCrLf
    s &= "        isIAssemblyFactory = asmDef.IsiAssemblyFactory" & vbCrLf
    s &= "    Catch" & vbCrLf
    s &= "        isIAssemblyFactory = False" & vbCrLf
    s &= "    End Try" & vbCrLf
    s &= vbCrLf
    s &= "    If Not isIAssemblyFactory Then" & vbCrLf
    s &= vbCrLf
    s &= "        Dim normalCount As Integer = 0" & vbCrLf
    s &= "        Dim obj As Object" & vbCrLf
    s &= vbCrLf
    s &= "        For Each obj In targets" & vbCrLf
    s &= vbCrLf
    s &= "            Dim occ As INV.ComponentOccurrence = TryCast(obj, INV.ComponentOccurrence)" & vbCrLf
    s &= vbCrLf
    s &= "            If occ Is Nothing Then Continue For" & vbCrLf
    s &= vbCrLf
    s &= "            Try" & vbCrLf
    s &= "                If activeState Then" & vbCrLf
    s &= "                    If occ.Suppressed Then" & vbCrLf
    s &= "                        occ.Unsuppress()" & vbCrLf
    s &= "                    End If" & vbCrLf
    s &= "                Else" & vbCrLf
    s &= "                    If Not occ.Suppressed Then" & vbCrLf
    s &= "                        occ.Suppress()" & vbCrLf
    s &= "                    End If" & vbCrLf
    s &= "                End If" & vbCrLf
    s &= "            Catch" & vbCrLf
    s &= "            End Try" & vbCrLf
    s &= vbCrLf
    s &= "            Try" & vbCrLf
    s &= "                If activeState Then" & vbCrLf
    s &= "                    If Not occ.Suppressed Then normalCount += 1" & vbCrLf
    s &= "                Else" & vbCrLf
    s &= "                    If occ.Suppressed Then normalCount += 1" & vbCrLf
    s &= "                End If" & vbCrLf
    s &= "            Catch" & vbCrLf
    s &= "            End Try" & vbCrLf
    s &= vbCrLf
    s &= "        Next" & vbCrLf
    s &= vbCrLf
    s &= "        Try" & vbCrLf
    s &= "            asmDoc.Update()" & vbCrLf
    s &= "            asmDoc.Save()" & vbCrLf
    s &= "        Catch" & vbCrLf
    s &= "        End Try" & vbCrLf
    s &= vbCrLf
    s &= "        Return normalCount" & vbCrLf
    s &= vbCrLf
    s &= "    End If" & vbCrLf
    s &= vbCrLf
    s &= "    Dim wantedExcluded As Boolean = Not activeState" & vbCrLf
    s &= "    Dim needsToggle As New System.Collections.ArrayList()" & vbCrLf
    s &= "    Dim alreadyCorrectCount As Integer = 0" & vbCrLf
    s &= "    Dim targetObj As Object" & vbCrLf
    s &= vbCrLf
    s &= "    For Each targetObj In targets" & vbCrLf
    s &= vbCrLf
    s &= "        Dim occ As INV.ComponentOccurrence = TryCast(targetObj, INV.ComponentOccurrence)" & vbCrLf
    s &= vbCrLf
    s &= "        If occ Is Nothing Then Continue For" & vbCrLf
    s &= vbCrLf
    s &= "        Dim currentExcluded As Boolean = IsOccurrenceExcludedInActiveIAssemblyRow(occ)" & vbCrLf
    s &= vbCrLf
    s &= "        If currentExcluded = wantedExcluded Then" & vbCrLf
    s &= "            alreadyCorrectCount += 1" & vbCrLf
    s &= "        Else" & vbCrLf
    s &= "            needsToggle.Add(occ)" & vbCrLf
    s &= "        End If" & vbCrLf
    s &= vbCrLf
    s &= "    Next" & vbCrLf
    s &= vbCrLf
    s &= "    If needsToggle.Count = 0 Then" & vbCrLf
    s &= "        Return alreadyCorrectCount" & vbCrLf
    s &= "    End If" & vbCrLf
    s &= vbCrLf
    s &= "    Try" & vbCrLf
    s &= "        asmDoc.SelectSet.Clear()" & vbCrLf
    s &= vbCrLf
    s &= "        Dim toggleObj As Object" & vbCrLf
    s &= vbCrLf
    s &= "        For Each toggleObj In needsToggle" & vbCrLf
    s &= vbCrLf
    s &= "            Dim occ As INV.ComponentOccurrence = TryCast(toggleObj, INV.ComponentOccurrence)" & vbCrLf
    s &= vbCrLf
    s &= "            If occ IsNot Nothing Then" & vbCrLf
    s &= "                asmDoc.SelectSet.Select(occ)" & vbCrLf
    s &= "            End If" & vbCrLf
    s &= vbCrLf
    s &= "        Next" & vbCrLf
    s &= vbCrLf
    s &= "        app.CommandManager.ControlDefinitions.Item(""ExcludeCtxCmd"").Execute()" & vbCrLf
    s &= vbCrLf
    s &= "        WF.Application.DoEvents()" & vbCrLf
    s &= vbCrLf
    s &= "        Try" & vbCrLf
    s &= "            asmDoc.Update()" & vbCrLf
    s &= "        Catch" & vbCrLf
    s &= "        End Try" & vbCrLf
    s &= vbCrLf
    s &= "        Try" & vbCrLf
    s &= "            asmDoc.SelectSet.Clear()" & vbCrLf
    s &= "        Catch" & vbCrLf
    s &= "        End Try" & vbCrLf
    s &= vbCrLf
    s &= "    Catch" & vbCrLf
    s &= "        Try" & vbCrLf
    s &= "            asmDoc.SelectSet.Clear()" & vbCrLf
    s &= "        Catch" & vbCrLf
    s &= "        End Try" & vbCrLf
    s &= "    End Try" & vbCrLf
    s &= vbCrLf
    s &= "    Dim changedCount As Integer = 0" & vbCrLf
    s &= "    Dim failed As New System.Collections.ArrayList()" & vbCrLf
    s &= "    Dim verifyObj As Object" & vbCrLf
    s &= vbCrLf
    s &= "    For Each verifyObj In needsToggle" & vbCrLf
    s &= vbCrLf
    s &= "        Dim occ As INV.ComponentOccurrence = TryCast(verifyObj, INV.ComponentOccurrence)" & vbCrLf
    s &= vbCrLf
    s &= "        If occ Is Nothing Then Continue For" & vbCrLf
    s &= vbCrLf
    s &= "        If IsOccurrenceExcludedInActiveIAssemblyRow(occ) = wantedExcluded Then" & vbCrLf
    s &= "            changedCount += 1" & vbCrLf
    s &= "        Else" & vbCrLf
    s &= "            failed.Add(occ)" & vbCrLf
    s &= "        End If" & vbCrLf
    s &= vbCrLf
    s &= "    Next" & vbCrLf
    s &= vbCrLf
    s &= "    If failed.Count > 0 Then" & vbCrLf
    s &= vbCrLf
    s &= "        Dim failedObj As Object" & vbCrLf
    s &= vbCrLf
    s &= "        For Each failedObj In failed" & vbCrLf
    s &= vbCrLf
    s &= "            Dim occ As INV.ComponentOccurrence = TryCast(failedObj, INV.ComponentOccurrence)" & vbCrLf
    s &= vbCrLf
    s &= "            If occ Is Nothing Then Continue For" & vbCrLf
    s &= vbCrLf
    s &= "            If SetMatchedTaggedOccurrenceActive(occ, activeState) Then" & vbCrLf
    s &= "                changedCount += 1" & vbCrLf
    s &= "            End If" & vbCrLf
    s &= vbCrLf
    s &= "        Next" & vbCrLf
    s &= vbCrLf
    s &= "    End If" & vbCrLf
    s &= vbCrLf
    s &= "    Try" & vbCrLf
    s &= "        asmDoc.Update()" & vbCrLf
    s &= "        asmDoc.Save()" & vbCrLf
    s &= "    Catch" & vbCrLf
    s &= "    End Try" & vbCrLf
    s &= vbCrLf
    s &= "    Return alreadyCorrectCount + changedCount" & vbCrLf
    s &= vbCrLf
    s &= "End Function" & vbCrLf
    s &= vbCrLf

    s &= "Private Function IsOccurrenceExcludedInActiveIAssemblyRow(occ As INV.ComponentOccurrence) As Boolean" & vbCrLf
    s &= vbCrLf
    s &= "    If occ Is Nothing Then Return False" & vbCrLf
    s &= vbCrLf
    s &= "    Dim app As INV.Application = ThisApplication" & vbCrLf
    s &= "    Dim asmDoc As INV.AssemblyDocument = TryCast(app.ActiveDocument, INV.AssemblyDocument)" & vbCrLf
    s &= vbCrLf
    s &= "    If asmDoc Is Nothing Then Return False" & vbCrLf
    s &= vbCrLf
    s &= "    Dim asmDef As INV.AssemblyComponentDefinition = asmDoc.ComponentDefinition" & vbCrLf
    s &= "    Dim factoryObj As Object = Nothing" & vbCrLf
    s &= "    Dim rowObj As Object = Nothing" & vbCrLf
    s &= vbCrLf
    s &= "    Try" & vbCrLf
    s &= "        factoryObj = CallByName(asmDef, ""iAssemblyFactory"", CallType.Get)" & vbCrLf
    s &= "    Catch" & vbCrLf
    s &= "        factoryObj = Nothing" & vbCrLf
    s &= "    End Try" & vbCrLf
    s &= vbCrLf
    s &= "    If factoryObj Is Nothing Then" & vbCrLf
    s &= vbCrLf
    s &= "        Try" & vbCrLf
    s &= "            Return occ.Suppressed" & vbCrLf
    s &= "        Catch" & vbCrLf
    s &= "            Return False" & vbCrLf
    s &= "        End Try" & vbCrLf
    s &= vbCrLf
    s &= "    End If" & vbCrLf
    s &= vbCrLf
    s &= "    Try" & vbCrLf
    s &= "        rowObj = CallByName(factoryObj, ""DefaultRow"", CallType.Get)" & vbCrLf
    s &= "    Catch" & vbCrLf
    s &= "        rowObj = Nothing" & vbCrLf
    s &= "    End Try" & vbCrLf
    s &= vbCrLf
    s &= "    If rowObj Is Nothing Then Return False" & vbCrLf
    s &= vbCrLf
    s &= "    Try" & vbCrLf
    s &= "        Return CBool(CallByName(rowObj, ""IsExcluded"", CallType.Method, occ))" & vbCrLf
    s &= "    Catch" & vbCrLf
    s &= "        Return False" & vbCrLf
    s &= "    End Try" & vbCrLf
    s &= vbCrLf
    s &= "End Function" & vbCrLf
    s &= vbCrLf

    s &= "Private Function SetMatchedTaggedOccurrenceActive(occ As INV.ComponentOccurrence, activeState As Boolean) As Boolean" & vbCrLf
    s &= vbCrLf
    s &= "    If occ Is Nothing Then Return False" & vbCrLf
    s &= vbCrLf
    s &= "    Dim app As INV.Application = ThisApplication" & vbCrLf
    s &= "    Dim asmDoc As INV.AssemblyDocument = TryCast(app.ActiveDocument, INV.AssemblyDocument)" & vbCrLf
    s &= vbCrLf
    s &= "    If asmDoc Is Nothing Then Return False" & vbCrLf
    s &= vbCrLf
    s &= "    Dim asmDef As INV.AssemblyComponentDefinition = asmDoc.ComponentDefinition" & vbCrLf
    s &= "    Dim isIAssemblyFactory As Boolean = False" & vbCrLf
    s &= vbCrLf
    s &= "    Try" & vbCrLf
    s &= "        isIAssemblyFactory = asmDef.IsiAssemblyFactory" & vbCrLf
    s &= "    Catch" & vbCrLf
    s &= "        isIAssemblyFactory = False" & vbCrLf
    s &= "    End Try" & vbCrLf
    s &= vbCrLf
    s &= "    If Not isIAssemblyFactory Then" & vbCrLf
    s &= vbCrLf
    s &= "        Try" & vbCrLf
    s &= "            If activeState Then" & vbCrLf
    s &= "                If occ.Suppressed Then" & vbCrLf
    s &= "                    occ.Unsuppress()" & vbCrLf
    s &= "                End If" & vbCrLf
    s &= "            Else" & vbCrLf
    s &= "                If Not occ.Suppressed Then" & vbCrLf
    s &= "                    occ.Suppress()" & vbCrLf
    s &= "                End If" & vbCrLf
    s &= "            End If" & vbCrLf
    s &= "        Catch" & vbCrLf
    s &= "        End Try" & vbCrLf
    s &= vbCrLf
    s &= "        Try" & vbCrLf
    s &= "            If activeState Then" & vbCrLf
    s &= "                Return Not occ.Suppressed" & vbCrLf
    s &= "            Else" & vbCrLf
    s &= "                Return occ.Suppressed" & vbCrLf
    s &= "            End If" & vbCrLf
    s &= "        Catch" & vbCrLf
    s &= "        End Try" & vbCrLf
    s &= vbCrLf
    s &= "        Return False" & vbCrLf
    s &= vbCrLf
    s &= "    End If" & vbCrLf
    s &= vbCrLf
    s &= "    Dim beforeExcluded As Boolean = IsOccurrenceExcludedInActiveIAssemblyRow(occ)" & vbCrLf
    s &= "    Dim wantedExcluded As Boolean = Not activeState" & vbCrLf
    s &= vbCrLf
    s &= "    If beforeExcluded = wantedExcluded Then" & vbCrLf
    s &= "        Return True" & vbCrLf
    s &= "    End If" & vbCrLf
    s &= vbCrLf
    s &= "    Try" & vbCrLf
    s &= "        asmDoc.SelectSet.Clear()" & vbCrLf
    s &= "        asmDoc.SelectSet.Select(occ)" & vbCrLf
    s &= vbCrLf
    s &= "        app.CommandManager.ControlDefinitions.Item(""ExcludeCtxCmd"").Execute()" & vbCrLf
    s &= vbCrLf
    s &= "        WF.Application.DoEvents()" & vbCrLf
    s &= vbCrLf
    s &= "        Try" & vbCrLf
    s &= "            asmDoc.Update()" & vbCrLf
    s &= "        Catch" & vbCrLf
    s &= "        End Try" & vbCrLf
    s &= vbCrLf
    s &= "        Try" & vbCrLf
    s &= "            asmDoc.SelectSet.Clear()" & vbCrLf
    s &= "        Catch" & vbCrLf
    s &= "        End Try" & vbCrLf
    s &= vbCrLf
    s &= "    Catch" & vbCrLf
    s &= "        Try" & vbCrLf
    s &= "            asmDoc.SelectSet.Clear()" & vbCrLf
    s &= "        Catch" & vbCrLf
    s &= "        End Try" & vbCrLf
    s &= vbCrLf
    s &= "        Return False" & vbCrLf
    s &= "    End Try" & vbCrLf
    s &= vbCrLf
    s &= "    Dim afterExcluded As Boolean = IsOccurrenceExcludedInActiveIAssemblyRow(occ)" & vbCrLf
    s &= vbCrLf
    s &= "    If afterExcluded = wantedExcluded Then" & vbCrLf
    s &= "        Try" & vbCrLf
    s &= "            asmDoc.Save()" & vbCrLf
    s &= "        Catch" & vbCrLf
    s &= "        End Try" & vbCrLf
    s &= vbCrLf
    s &= "        Return True" & vbCrLf
    s &= "    End If" & vbCrLf
    s &= vbCrLf
    s &= "    Return False" & vbCrLf
    s &= vbCrLf
    s &= "End Function" & vbCrLf
    s &= vbCrLf

    s &= "Private Function SetFeatureActiveByTag(topAsm As INV.AssemblyDocument, tagNs As String, tagKey As String, wantedTag As String, featureName As String, activeState As Boolean) As Integer" & vbCrLf
    s &= vbCrLf
    s &= "    Dim count As Integer = 0" & vbCrLf
    s &= "    Dim tempRuleName As String = ""__TEMP_TAG_FEATURE_ACTIVE""" & vbCrLf
    s &= "    Dim tempRuleFolder As String = GetFirstExternalRuleDirectory()" & vbCrLf
    s &= vbCrLf
    s &= "    If String.IsNullOrWhiteSpace(tempRuleFolder) Then" & vbCrLf
    s &= "        WF.MessageBox.Show(""No iLogic external rule directory was found."", ""Internal CAD Tag"")" & vbCrLf
    s &= "        Return 0" & vbCrLf
    s &= "    End If" & vbCrLf
    s &= vbCrLf
    s &= "    Dim tempRulePath As String = IO.Path.Combine(tempRuleFolder, tempRuleName & "".vb"")" & vbCrLf
    s &= "    Dim ruleText As String = """"" & vbCrLf
    s &= vbCrLf
    s &= "    ruleText &= ""Sub Main()"" & vbCrLf" & vbCrLf
    s &= "    ruleText &= ""    Feature.IsActive("""""" & featureName & """""") = "" & If(activeState, ""True"", ""False"") & vbCrLf" & vbCrLf
    s &= "    ruleText &= ""End Sub"" & vbCrLf" & vbCrLf
    s &= vbCrLf
    s &= "    IO.File.WriteAllText(tempRulePath, ruleText)" & vbCrLf
    s &= vbCrLf
    s &= "    Dim d As INV.Document" & vbCrLf
    s &= vbCrLf
    s &= "    For Each d In topAsm.AllReferencedDocuments" & vbCrLf
    s &= vbCrLf
    s &= "        If d Is Nothing Then Continue For" & vbCrLf
    s &= "        If d.DocumentType <> INV.DocumentTypeEnum.kPartDocumentObject Then Continue For" & vbCrLf
    s &= vbCrLf
    s &= "        Dim p As INV.PartDocument = TryCast(d, INV.PartDocument)" & vbCrLf
    s &= vbCrLf
    s &= "        If p Is Nothing Then Continue For" & vbCrLf
    s &= vbCrLf
    s &= "        If HasTagValue(p, tagNs, tagKey, wantedTag) OrElse HasTagValue(p.ComponentDefinition, tagNs, tagKey, wantedTag) Then" & vbCrLf
    s &= vbCrLf
    s &= "            Try" & vbCrLf
    s &= "                iLogicVb.Automation.RunExternalRule(p, tempRuleName)" & vbCrLf
    s &= "                count += 1" & vbCrLf
    s &= "            Catch ex As Exception" & vbCrLf
    s &= "                WF.MessageBox.Show(""Failed on tagged part:"" & vbCrLf & p.FullFileName & vbCrLf & vbCrLf & ""Rule path:"" & vbCrLf & tempRulePath & vbCrLf & vbCrLf & ex.Message, ""Internal CAD Tag"")" & vbCrLf
    s &= "            End Try" & vbCrLf
    s &= vbCrLf
    s &= "        End If" & vbCrLf
    s &= vbCrLf
    s &= "    Next" & vbCrLf
    s &= vbCrLf
    s &= "    Try" & vbCrLf
    s &= "        If IO.File.Exists(tempRulePath) Then" & vbCrLf
    s &= "            IO.File.Delete(tempRulePath)" & vbCrLf
    s &= "        End If" & vbCrLf
    s &= "    Catch" & vbCrLf
    s &= "    End Try" & vbCrLf
    s &= vbCrLf
    s &= "    Return count" & vbCrLf
    s &= vbCrLf
    s &= "End Function" & vbCrLf
    s &= vbCrLf

    s &= "Private Function GetFirstExternalRuleDirectory() As String" & vbCrLf
    s &= vbCrLf
    s &= "    Try" & vbCrLf
    s &= "        Dim dirs As Object = iLogicVb.Automation.FileOptions.ExternalRuleDirectories" & vbCrLf
    s &= "        Dim d As String" & vbCrLf
    s &= vbCrLf
    s &= "        For Each d In dirs" & vbCrLf
    s &= "            If Not String.IsNullOrWhiteSpace(d) Then" & vbCrLf
    s &= "                If IO.Directory.Exists(d) Then" & vbCrLf
    s &= "                    Return d" & vbCrLf
    s &= "                End If" & vbCrLf
    s &= "            End If" & vbCrLf
    s &= "        Next" & vbCrLf
    s &= "    Catch" & vbCrLf
    s &= "    End Try" & vbCrLf
    s &= vbCrLf
    s &= "    Return """"" & vbCrLf
    s &= vbCrLf
    s &= "End Function" & vbCrLf

    GetGeneratedHelperCode = s

End Function

Private Sub ShowCodeHelp(tagNs As String, tagKey As String)

    Dim helpLines As String() = {
        "# Internal CAD Tag Action Recorder",
        "",
        "## Purpose",
        "",
        "The Internal CAD Tag Action Recorder is an Autodesk Inventor iLogic tool used to mark parts and assemblies with internal CAD tags, find those tags later, record actions against tagged files, and generate replayable iLogic code.",
        "",
        "The core use case is simple:",
        "",
        "1. Tag a file or selected occurrence document.",
        "2. Record an action such as suppress occurrence, unsuppress occurrence, suppress feature, or unsuppress feature.",
        "3. Generate replayable iLogic code.",
        "4. Run the replay code later against the same assembly structure.",
        "",
        "The tool is intended for repeatable CAD cleanup, configuration, and automation work where selected components or part features must be controlled by a stable internal tag rather than by browser name alone.",
        "",
        "## High level architecture",
        "",
        "The tool has four main layers.",
        "",
        "1. Tag storage layer",
        "2. User action layer",
        "3. Recorder layer",
        "4. Generated replay layer",
        "",
        "The tag storage layer writes and reads Inventor AttributeSets.",
        "",
        "The user action layer provides buttons for writing tags, removing tags, searching tags, recording occurrence actions, recording feature actions, showing generated code, and clearing recorded steps.",
        "",
        "The recorder layer writes compact action records to a temporary text file.",
        "",
        "The generated replay layer converts those compact records into a standalone iLogic rule that can reproduce the recorded actions.",
        "",
        "## Core constants",
        "",
        "The live recorder uses these tag constants.",
        "",
        "```vb",
        "Const TAG_NS As String = """ & tagNs & """",
        "Const TAG_KEY As String = """ & tagKey & """",
        "Const DATE_KEY As String = ""TaggedDate""",
        "Const USER_KEY As String = ""TaggedBy""",
        "Const DOC_TYPE_KEY As String = ""TaggedDocumentType""",
        "```",
        "",
        "`TAG_NS` is the AttributeSet name.",
        "",
        "`TAG_KEY` is the main internal CAD tag value.",
        "",
        "`DATE_KEY` stores when the tag was written.",
        "",
        "`USER_KEY` stores who wrote the tag.",
        "",
        "`DOC_TYPE_KEY` stores whether the tagged file was treated as a part or an assembly.",
        "",
        "## Tag storage model",
        "",
        "The tool writes the same tag to two locations when possible.",
        "",
        "```text",
        "Document object",
        "ComponentDefinition object",
        "```",
        "",
        "For a part, this means:",
        "",
        "```text",
        "PartDocument",
        "PartDocument.ComponentDefinition",
        "```",
        "",
        "For an assembly, this means:",
        "",
        "```text",
        "AssemblyDocument",
        "AssemblyDocument.ComponentDefinition",
        "```",
        "",
        "This dual write is intentional. Some Inventor contexts expose document attributes more reliably, while other contexts expose component definition attributes more reliably.",
        "",
        "When checking for a matching tag, the code should check both locations.",
        "",
        "```vb",
        "HasTagValue(occDoc, TAG_NS, TAG_KEY, wantedTag)",
        "HasComponentDefinitionTagValue(occDoc, TAG_NS, TAG_KEY, wantedTag)",
        "```",
        "",
        "A match is valid if either location contains the requested tag.",
        "",
        "## What a tag represents",
        "",
        "A tag represents the file identity or automation group you want the tool to act on.",
        "",
        "The tag is not the occurrence name.",
        "",
        "The tag is not the file name.",
        "",
        "The tag is not the feature name.",
        "",
        "The tag is a stable internal marker written into the Inventor document attributes.",
        "",
        "Occurrence names can change.",
        "",
        "Browser names can change.",
        "",
        "File paths can move.",
        "",
        "The tag is meant to remain a stable automation target.",
        "",
        "## User interface actions",
        "",
        "### WRITE TAG",
        "",
        "Writes the custom tag to the active part or active assembly.",
        "",
        "When the active document is a part, the tool writes to the part document and part component definition.",
        "",
        "When the active document is an assembly, the tool writes to the assembly document and assembly component definition.",
        "",
        "After writing the tag, the file is saved.",
        "",
        "### REMOVE TAG",
        "",
        "Removes the internal CAD tag.",
        "",
        "The removal form supports two logical scopes.",
        "",
        "```text",
        "SPECIFIC",
        "ALL",
        "```",
        "",
        "`SPECIFIC` removes tags from the current open file only.",
        "",
        "`ALL` removes tags from the current assembly and all referenced parts and assemblies.",
        "",
        "Each file can contain up to two tag locations:",
        "",
        "```text",
        "Document level",
        "Component definition level",
        "```",
        "",
        "The removal count is a tag location count, not a file count.",
        "",
        "### CHECK TAG",
        "",
        "Searches the current assembly for one exact tag name.",
        "",
        "The search checks the top assembly first, then iterates referenced documents.",
        "",
        "The result reports checked assemblies, checked parts, and matching tagged files.",
        "",
        "### SEARCH ALL",
        "",
        "Searches the current assembly for every internal CAD tag.",
        "",
        "This is an audit action.",
        "",
        "It reports all found tags, tagged date, tagged user, and tagged document type when available.",
        "",
        "### CODE HELP",
        "",
        "Shows this internal reference document in a copyable text box.",
        "",
        "The output is Markdown style so it can also be saved as a SKILL.md reference document.",
        "",
        "### SUPPRESS OCC",
        "",
        "Records and runs a tag based occurrence suppression action.",
        "",
        "The user selects one occurrence.",
        "",
        "The tool resolves the effective tag for that selected occurrence.",
        "",
        "If the selected occurrence document already has a tag, that tag is used.",
        "",
        "If the selected occurrence document does not have a tag, the tool asks whether to write the current typed tag to the selected occurrence document.",
        "",
        "After a tag is resolved, the tool finds all matching tagged occurrences and suppresses or excludes them.",
        "",
        "Then it records:",
        "",
        "```text",
        "SUPPRESS_OCC|TagName",
        "```",
        "",
        "### UNSUPPRESS OCC",
        "",
        "Records and runs a tag based occurrence unsuppression action.",
        "",
        "The user can type the tag directly or select one occurrence to read its tag.",
        "",
        "After a tag is resolved, the tool finds all matching tagged occurrences and unsuppresses or includes them.",
        "",
        "Then it records:",
        "",
        "```text",
        "UNSUPPRESS_OCC|TagName",
        "```",
        "",
        "### SUPPRESS FEATURE",
        "",
        "Records and runs a part feature suppression action.",
        "",
        "The user must run this while a part file is active.",
        "",
        "The tool resolves the effective tag for the active file.",
        "",
        "The user selects a feature from the model tree.",
        "",
        "The tool reads the selected feature name and suppresses it.",
        "",
        "Then it records:",
        "",
        "```text",
        "SUPPRESS_FEATURE|TagName|FeatureName",
        "```",
        "",
        "### UNSUPPRESS FEATURE",
        "",
        "Records and runs a part feature unsuppression action.",
        "",
        "The user must run this while a part file is active.",
        "",
        "The tool resolves the effective tag for the active file.",
        "",
        "The user selects a feature from the model tree.",
        "",
        "The tool reads the selected feature name and unsuppresses it.",
        "",
        "Then it records:",
        "",
        "```text",
        "UNSUPPRESS_FEATURE|TagName|FeatureName",
        "```",
        "",
        "### SHOW GENERATED CODE",
        "",
        "Reads the recorder file and builds a standalone iLogic replay rule.",
        "",
        "The generated code appears in a copyable text box.",
        "",
        "### CLEAR STEPS",
        "",
        "Deletes the recorder file.",
        "",
        "Use this when the next generated replay code should contain only new actions.",
        "",
        "## Recorder file",
        "",
        "The recorder file is stored in the Windows temp folder.",
        "",
        "```vb",
        "Dim recorderFile As String = IO.Path.Combine(IO.Path.GetTempPath(), ""InternalCadTag_ActionRecorder.txt"")",
        "```",
        "",
        "Each recorded action is stored as one line.",
        "",
        "Occurrence action format:",
        "",
        "```text",
        "SUPPRESS_OCC|TagName",
        "UNSUPPRESS_OCC|TagName",
        "```",
        "",
        "Feature action format:",
        "",
        "```text",
        "SUPPRESS_FEATURE|TagName|FeatureName",
        "UNSUPPRESS_FEATURE|TagName|FeatureName",
        "```",
        "",
        "When a new recordable action starts and the file already has content, the tool asks whether to clear previous steps.",
        "",
        "Yes means delete the old recorder file and continue.",
        "",
        "No means append the new action to the existing recorder file.",
        "",
        "## Generated replay code",
        "",
        "The generated replay code is built by `BuildGeneratedCode` and `GetGeneratedHelperCode`.",
        "",
        "`BuildGeneratedCode` creates the top level replay rule.",
        "",
        "`GetGeneratedHelperCode` appends all helper functions needed by the replay rule.",
        "",
        "The generated replay code includes this startup pattern.",
        "",
        "```vb",
        "AddReference ""System.Windows.Forms.dll""",
        "Imports INV = Inventor",
        "Imports WF = System.Windows.Forms",
        "Imports IO = System.IO",
        "",
        "Sub Main()",
        "    Const TAG_NS As String = ""INTERNAL_CAD_TAG""",
        "    Const TAG_KEY As String = ""TagName""",
        "",
        "    Dim app As INV.Application = ThisApplication",
        "    Dim activeDoc As INV.Document = app.ActiveDocument",
        "    Dim asm As INV.AssemblyDocument = TryCast(activeDoc, INV.AssemblyDocument)",
        "    Dim part As INV.PartDocument = TryCast(activeDoc, INV.PartDocument)",
        "    Dim txn As INV.Transaction = Nothing",
        "```",
        "",
        "The generated replay code starts an Inventor transaction.",
        "",
        "```vb",
        "txn = app.TransactionManager.StartTransaction(activeDoc, ""Internal CAD Tag Replay"")",
        "```",
        "",
        "If the replay succeeds, the transaction is ended.",
        "",
        "If an exception occurs, the transaction is aborted.",
        "",
        "This gives the generated replay rule a cleaner undo behavior.",
        "",
        "## Generated replay occurrence pipeline",
        "",
        "Occurrence replay actions use this pipeline.",
        "",
        "```text",
        "Recorded tag",
        "Search assembly occurrence tree",
        "Collect all matching occurrences",
        "Apply desired active state",
        "Verify result",
        "Save once",
        "```",
        "",
        "The generated suppress call should be:",
        "",
        "```vb",
        "SuppressOccurrencesByTag(asm.ComponentDefinition.Occurrences, TAG_NS, TAG_KEY, ""TagName"")",
        "```",
        "",
        "The generated unsuppress call should be:",
        "",
        "```vb",
        "UnsuppressOccurrencesByTagSafe(asm.ComponentDefinition.Occurrences, TAG_NS, TAG_KEY, ""TagName"")",
        "```",
        "",
        "Both functions should use the queued pipeline.",
        "",
        "## Queued occurrence processing",
        "",
        "The queued method is the current preferred method.",
        "",
        "The older method toggled each occurrence immediately during search.",
        "",
        "The faster method separates search from action.",
        "",
        "The faster method does this.",
        "",
        "1. Search all matching tagged occurrences.",
        "2. Store each match in `System.Collections.ArrayList`.",
        "3. Determine which matches already have the desired state.",
        "4. For iAssemblies, multi select only occurrences that need the toggle.",
        "5. Run `ExcludeCtxCmd` once.",
        "6. Verify every queued occurrence.",
        "7. Fall back to one by one only for failures.",
        "8. Update and save once at the end.",
        "",
        "This avoids repeated update and save calls inside the recursive search loop.",
        "",
        "This is especially important for iAssembly exclusions because UI command execution and model updates are expensive.",
        "",
        "## Required queued helper functions",
        "",
        "Generated code should include these occurrence helpers.",
        "",
        "```text",
        "SuppressOccurrencesByTag",
        "UnsuppressOccurrencesByTagSafe",
        "CollectOccurrencesByTag",
        "ApplyQueuedMatchedTaggedOccurrencesActive",
        "SetMatchedTaggedOccurrenceActive",
        "IsOccurrenceExcludedInActiveIAssemblyRow",
        "```",
        "",
        "## Normal assembly occurrence path",
        "",
        "Normal assemblies should use the normal API path.",
        "",
        "For suppress:",
        "",
        "```vb",
        "If Not occ.Suppressed Then",
        "    occ.Suppress()",
        "End If",
        "```",
        "",
        "For unsuppress:",
        "",
        "```vb",
        "If occ.Suppressed Then",
        "    occ.Unsuppress()",
        "End If",
        "```",
        "",
        "Normal assemblies do not need `ExcludeCtxCmd`.",
        "",
        "Normal assemblies do not need iAssembly row verification.",
        "",
        "## iAssembly occurrence path",
        "",
        "iAssembly factories do not behave like normal assemblies for occurrence suppression.",
        "",
        "Direct occurrence suppression can fail with invalid argument errors.",
        "",
        "Direct table cell assignment can fail with COM errors.",
        "",
        "The verified working path is to use Inventor's own context command.",
        "",
        "```vb",
        "app.CommandManager.ControlDefinitions.Item(""ExcludeCtxCmd"").Execute()",
        "```",
        "",
        "`ExcludeCtxCmd` behaves like the right click Exclude checkbox.",
        "",
        "If the occurrence is currently included, running the command excludes it.",
        "",
        "If the occurrence is currently excluded, running the command includes it.",
        "",
        "Because it is a toggle, the code must check current state before running it.",
        "",
        "## iAssembly desired state logic",
        "",
        "The generated code uses this logic.",
        "",
        "```vb",
        "Dim beforeExcluded As Boolean = IsOccurrenceExcludedInActiveIAssemblyRow(occ)",
        "Dim wantedExcluded As Boolean = Not activeState",
        "",
        "If beforeExcluded = wantedExcluded Then",
        "    Return True",
        "End If",
        "```",
        "",
        "`activeState = False` means the occurrence should be suppressed or excluded.",
        "",
        "`activeState = True` means the occurrence should be unsuppressed or included.",
        "",
        "Therefore:",
        "",
        "```vb",
        "Dim wantedExcluded As Boolean = Not activeState",
        "```",
        "",
        "When wanted state differs from current state, the code selects the occurrence and runs `ExcludeCtxCmd`.",
        "",
        "## iAssembly state verification",
        "",
        "The code verifies iAssembly state with the active iAssembly factory row.",
        "",
        "```vb",
        "Return CBool(CallByName(rowObj, ""IsExcluded"", CallType.Method, occ))",
        "```",
        "",
        "If the active document is not an iAssembly factory, the helper falls back to `occ.Suppressed`.",
        "",
        "This makes the same helper usable in both normal assembly and iAssembly contexts.",
        "",
        "## Why direct Excluded property is not used",
        "",
        "Do not use this:",
        "",
        "```vb",
        "occ.Excluded = False",
        "```",
        "",
        "In this Inventor iLogic context, `Excluded` was not available on the selected `ComponentOccurrence` object.",
        "",
        "The observed error was member not found.",
        "",
        "This means the selected occurrence cannot be controlled through a simple `occ.Excluded` property.",
        "",
        "## Why direct table cell editing is not used",
        "",
        "The iAssembly table can show a column like this:",
        "",
        "```text",
        "ASSIEME RUOTA:1:Include/Exclude",
        "```",
        "",
        "The cell value can show:",
        "",
        "```text",
        "Exclude",
        "```",
        "",
        "However, direct cell assignment can still fail.",
        "",
        "Example of the unreliable path:",
        "",
        "```vb",
        "CallByName(cellObj, ""Value"", CallType.Set, ""Include"")",
        "```",
        "",
        "Even when the column exists and the value is visible, Inventor may reject direct assignment with an unspecified COM error.",
        "",
        "Because right click Exclude works reliably, the correct automation path is to preselect the occurrence and run `ExcludeCtxCmd`.",
        "",
        "## Why Component.IsActive is not the main path",
        "",
        "Do not use this as the primary iAssembly method:",
        "",
        "```vb",
        "Component.IsActive(occ.Name) = False",
        "```",
        "",
        "`Component.IsActive` can be useful in simple iLogic cases, but it was not reliable for the iAssembly occurrence case handled by this tool.",
        "",
        "The tag system still finds by tag.",
        "",
        "The occurrence name is only a transient handle and should not become the targeting method.",
        "",
        "## Tag based targeting rule",
        "",
        "The action target is always the tag.",
        "",
        "The tool should never become name based.",
        "",
        "Correct logic:",
        "",
        "```text",
        "Find matching document tag",
        "Get the matching occurrence object",
        "Apply the state change to that occurrence object",
        "```",
        "",
        "Incorrect logic:",
        "",
        "```text",
        "Search by occurrence browser name",
        "Suppress by occurrence browser name",
        "```",
        "",
        "Occurrence names are only used indirectly by Inventor when a selected occurrence is passed to the command system.",
        "",
        "## Feature replay pipeline",
        "",
        "Feature actions are different from occurrence actions.",
        "",
        "Feature actions target part features by feature name on tagged part documents.",
        "",
        "The generated feature replay uses a temporary external iLogic rule.",
        "",
        "The temp rule name is:",
        "",
        "```text",
        "__TEMP_TAG_FEATURE_ACTIVE",
        "```",
        "",
        "The generated temp rule body is:",
        "",
        "```vb",
        "Sub Main()",
        "    Feature.IsActive(""FeatureName"") = True",
        "End Sub",
        "```",
        "",
        "or:",
        "",
        "```vb",
        "Sub Main()",
        "    Feature.IsActive(""FeatureName"") = False",
        "End Sub",
        "```",
        "",
        "The tool writes the temp rule into the first valid external rule directory.",
        "",
        "Then it runs that external rule against each tagged part.",
        "",
        "After processing, it attempts to delete the temporary rule file.",
        "",
        "## Required generated helper map",
        "",
        "A complete generated replay rule should include these helpers.",
        "",
        "### Tag helpers",
        "",
        "```text",
        "HasTagValue",
        "GetTagValue",
        "HasComponentDefinitionTagValue",
        "```",
        "",
        "### Document resolution helpers",
        "",
        "```text",
        "GetOccurrenceDocumentSafe",
        "```",
        "",
        "### Occurrence action helpers",
        "",
        "```text",
        "SuppressOccurrencesByTag",
        "UnsuppressOccurrencesByTagSafe",
        "CollectOccurrencesByTag",
        "ApplyQueuedMatchedTaggedOccurrencesActive",
        "SetMatchedTaggedOccurrenceActive",
        "IsOccurrenceExcludedInActiveIAssemblyRow",
        "```",
        "",
        "### Feature action helpers",
        "",
        "```text",
        "SetFeatureActiveByTag",
        "GetFirstExternalRuleDirectory",
        "```",
        "",
        "## Helpers that should not be generated anymore",
        "",
        "These helpers are old or unreliable and should not be emitted by `GetGeneratedHelperCode`.",
        "",
        "```text",
        "SetOccurrenceSuppressedOrExcluded",
        "SetIAssemblyOccurrenceIncludedByRowCell",
        "SetIAssemblyOccurrenceExcludedByRowCell",
        "SetIAssemblyOccurrenceExcludedStateByRowCell",
        "UnsuppressOccurrencesByTag",
        "```",
        "",
        "`SetOccurrenceSuppressedOrExcluded` used older suppression logic and does not handle iAssembly factories correctly.",
        "",
        "`SetIAssemblyOccurrenceIncludedByRowCell`, `SetIAssemblyOccurrenceExcludedByRowCell`, and `SetIAssemblyOccurrenceExcludedStateByRowCell` rely on direct table cell assignment, which is not reliable in this context.",
        "",
        "`UnsuppressOccurrencesByTag` is the older unsafe unsuppress helper and should be replaced by `UnsuppressOccurrencesByTagSafe`.",
        "",
        "## Document resolution strategy",
        "",
        "Suppressed or excluded occurrences may not expose their document through the simplest path.",
        "",
        "The helper should try multiple paths.",
        "",
        "First:",
        "",
        "```vb",
        "occ.Definition.Document",
        "```",
        "",
        "Then:",
        "",
        "```vb",
        "occ.ReferencedDocumentDescriptor.ReferencedDocument",
        "```",
        "",
        "Then:",
        "",
        "```vb",
        "occ.ReferencedDocumentDescriptor.FullDocumentName",
        "ThisApplication.Documents.Open(fullName, False)",
        "```",
        "",
        "Then:",
        "",
        "```vb",
        "occ.ReferencedFileDescriptor.FullFileName",
        "ThisApplication.Documents.Open(fileName, False)",
        "```",
        "",
        "This makes the tag search more resilient when components are suppressed, excluded, or not fully resolved.",
        "",
        "## Normal suppress replay example",
        "",
        "Generated suppress replay should require an assembly.",
        "",
        "```vb",
        "If asm Is Nothing Then",
        "    WF.MessageBox.Show(""Open an assembly first for occurrence suppression."")",
        "    Exit Sub",
        "End If",
        "",
        "SuppressOccurrencesByTag(asm.ComponentDefinition.Occurrences, TAG_NS, TAG_KEY, ""MyTag"")",
        "```",
        "",
        "## Normal unsuppress replay example",
        "",
        "Generated unsuppress replay should require an assembly.",
        "",
        "```vb",
        "If asm Is Nothing Then",
        "    WF.MessageBox.Show(""Open an assembly first for occurrence unsuppression."")",
        "    Exit Sub",
        "End If",
        "",
        "UnsuppressOccurrencesByTagSafe(asm.ComponentDefinition.Occurrences, TAG_NS, TAG_KEY, ""MyTag"")",
        "```",
        "",
        "## Normal feature suppress replay example",
        "",
        "If the active document is an assembly, feature replay searches all referenced parts.",
        "",
        "```vb",
        "SetFeatureActiveByTag(asm, TAG_NS, TAG_KEY, ""MyTag"", ""FeatureName"", False)",
        "```",
        "",
        "If the active document is a part, feature replay checks the active part tag and directly uses `Feature.IsActive`.",
        "",
        "```vb",
        "Feature.IsActive(""FeatureName"") = False",
        "```",
        "",
        "## Normal feature unsuppress replay example",
        "",
        "If the active document is an assembly, feature replay searches all referenced parts.",
        "",
        "```vb",
        "SetFeatureActiveByTag(asm, TAG_NS, TAG_KEY, ""MyTag"", ""FeatureName"", True)",
        "```",
        "",
        "If the active document is a part, feature replay checks the active part tag and directly uses `Feature.IsActive`.",
        "",
        "```vb",
        "Feature.IsActive(""FeatureName"") = True",
        "```",
        "",
        "## Recommended workflow for creating a suppress replay",
        "",
        "1. Open the top level assembly.",
        "2. Run the action recorder.",
        "3. Enter the intended custom tag.",
        "4. Click `SUPPRESS OCC`.",
        "5. Select one occurrence that represents the target group.",
        "6. Let the tool resolve or write the tag.",
        "7. Let the action run once.",
        "8. Review the generated replay code.",
        "9. Copy the generated replay code into a new iLogic rule.",
        "10. Test the generated rule.",
        "",
        "## Recommended workflow for creating an unsuppress replay",
        "",
        "1. Open the top level assembly.",
        "2. Run the action recorder.",
        "3. Click `UNSUPPRESS OCC`.",
        "4. Type the tag or choose `Select Occurrence`.",
        "5. Let the action run once.",
        "6. Review the generated replay code.",
        "7. Copy the generated replay code into a new iLogic rule.",
        "8. Test the generated rule.",
        "",
        "## Recommended workflow for feature actions",
        "",
        "1. Open the tagged part.",
        "2. Run the action recorder.",
        "3. Click `SUPPRESS FEATURE` or `UNSUPPRESS FEATURE`.",
        "4. Select the feature from the model tree.",
        "5. Confirm the generated replay code.",
        "6. Run the generated replay from a part or assembly context as needed.",
        "",
        "## Performance notes",
        "",
        "The fastest proven occurrence approach is queued processing.",
        "",
        "Do not update and save inside every recursive match.",
        "",
        "Do not run `ExcludeCtxCmd` one occurrence at a time unless the multi select path fails.",
        "",
        "Do not repeatedly open message boxes during batch processing.",
        "",
        "Do not add logging inside the replay path unless specifically debugging.",
        "",
        "Use one final update and save after the queued operation.",
        "",
        "## Known limitations",
        "",
        "1. The iAssembly command path depends on `ExcludeCtxCmd` being available in the current Inventor context.",
        "2. The command path depends on the occurrence being selectable.",
        "3. Direct table cell editing may fail even when the Include or Exclude column exists.",
        "4. Suppressed or excluded occurrences may not always resolve their referenced document.",
        "5. Feature actions depend on exact feature names.",
        "6. Feature actions require a valid external iLogic rule directory when replayed against referenced parts.",
        "7. The generated replay assumes the active document context is correct.",
        "",
        "## Troubleshooting duplicate function errors",
        "",
        "If the iLogic rule reports multiple definitions with identical signatures, search for the duplicated function and keep only one copy.",
        "",
        "Common duplicates:",
        "",
        "```text",
        "HasTagValue",
        "GetTagValue",
        "GetOccurrenceDocumentSafe",
        "HasComponentDefinitionTagValue",
        "SuppressOccurrencesByTag",
        "UnsuppressOccurrencesByTagSafe",
        "CollectOccurrencesByTag",
        "ApplyQueuedMatchedTaggedOccurrencesActive",
        "IsOccurrenceExcludedInActiveIAssemblyRow",
        "SetMatchedTaggedOccurrenceActive",
        "```",
        "",
        "Duplicate functions usually happen after pasting helper code more than once.",
        "",
        "## Troubleshooting iAssembly include or exclude",
        "",
        "If an iAssembly occurrence does not include or exclude, test the command directly.",
        "",
        "Expected behavior when currently excluded:",
        "",
        "```text",
        "Excluded before: True",
        "Excluded after: False",
        "```",
        "",
        "Expected behavior when currently included:",
        "",
        "```text",
        "Excluded before: False",
        "Excluded after: True",
        "```",
        "",
        "If this direct toggle works, generated replay should use the same `ExcludeCtxCmd` toggle path.",
        "",
        "If direct toggle fails, verify the occurrence is selectable and that the active document is the iAssembly factory.",
        "",
        "## Troubleshooting generated code missing queue logic",
        "",
        "If generated replay code still suppresses or unsuppresses one item at a time, replace `GetGeneratedHelperCode` with the version that emits these functions:",
        "",
        "```text",
        "CollectOccurrencesByTag",
        "ApplyQueuedMatchedTaggedOccurrencesActive",
        "```",
        "",
        "Then regenerate the replay code.",
        "",
        "## Troubleshooting missing external rule directory",
        "",
        "Feature replay against referenced parts requires an external iLogic rule directory.",
        "",
        "The helper reads:",
        "",
        "```vb",
        "iLogicVb.Automation.FileOptions.ExternalRuleDirectories",
        "```",
        "",
        "If no valid directory exists, feature replay cannot create the temporary rule.",
        "",
        "Set an external rule directory in Inventor iLogic configuration before using generated feature replay.",
        "",
        "## Maintenance rules",
        "",
        "1. Keep tag based targeting as the core behavior.",
        "2. Do not convert occurrence actions to name based targeting.",
        "3. Keep normal assembly and iAssembly logic separate.",
        "4. Keep `ExcludeCtxCmd` as the iAssembly toggle method.",
        "5. Keep queued occurrence processing in generated replay code.",
        "6. Keep the one by one fallback for failed queued toggles.",
        "7. Do not reintroduce direct iAssembly table cell assignment.",
        "8. Do not reintroduce `occ.Excluded`.",
        "9. Do not generate old unsafe unsuppress helpers.",
        "10. Keep generated code self contained.",
        "",
        "## Current best known occurrence logic",
        "",
        "The current best known occurrence logic is:",
        "",
        "```text",
        "Find tagged occurrence documents",
        "Queue the matching occurrences",
        "For normal assemblies, call Suppress or Unsuppress",
        "For iAssemblies, compare IsExcluded to wanted state",
        "Multi select occurrences that need toggling",
        "Run ExcludeCtxCmd once",
        "Verify",
        "Fallback one by one only where needed",
        "Update and save once",
        "```",
        "",
        "## Current best known iAssembly rule",
        "",
        "Use `ExcludeCtxCmd` as a toggle.",
        "",
        "Never run it blindly.",
        "",
        "Always check `IsExcluded` before running it.",
        "",
        "Always verify `IsExcluded` after running it.",
        "",
        "## Current best known generated replay rule",
        "",
        "Generated replay should be fully self contained.",
        "",
        "It should not depend on the original recorder rule.",
        "",
        "It should include all tag helpers, document helpers, occurrence helpers, queue helpers, iAssembly helpers, feature helpers, and external rule directory helpers.",
        "",
        "## End of internal reference"
    }

    Dim helpText As String = String.Join(vbCrLf, helpLines)

    Dim resultForm As New WF.Form()
    resultForm.Text = "Internal CAD Tag Code Help"
    resultForm.StartPosition = WF.FormStartPosition.CenterParent
    resultForm.Width = 1100
    resultForm.Height = 800

    Dim resultBox As New WF.TextBox()
    resultBox.Multiline = True
    resultBox.ReadOnly = False
    resultBox.ScrollBars = WF.ScrollBars.Both
    resultBox.WordWrap = False
    resultBox.Dock = WF.DockStyle.Fill
    resultBox.Font = New SD.Font("Consolas", 9.0!)
    resultBox.Text = helpText

    resultForm.Controls.Add(resultBox)
    resultForm.ShowDialog()

End Sub

Private Function ShowRemoveTagScopeForm() As String

    Dim f As New WF.Form()
    f.Text = "Remove Internal CAD Tag"
    f.FormBorderStyle = WF.FormBorderStyle.FixedDialog
    f.StartPosition = WF.FormStartPosition.CenterParent
    f.MinimizeBox = False
    f.MaximizeBox = False
    f.Width = 430
    f.Height = 155

    Dim lbl As New WF.Label()
    lbl.Left = 12
    lbl.Top = 14
    lbl.Width = 390
    lbl.Text = "Remove the internal CAD tag from a specific component or all components?"
    f.Controls.Add(lbl)

    Dim btnSpecific As New WF.Button()
    btnSpecific.Text = "Specific Component"
    btnSpecific.Width = 140
    btnSpecific.Height = 30
    btnSpecific.Left = 12
    btnSpecific.Top = 65
    btnSpecific.Tag = "SPECIFIC"
    AddHandler btnSpecific.Click, AddressOf ScopeButtonClick
    f.Controls.Add(btnSpecific)

    Dim btnAll As New WF.Button()
    btnAll.Text = "All Components"
    btnAll.Width = 120
    btnAll.Height = 30
    btnAll.Left = 162
    btnAll.Top = 65
    btnAll.Tag = "ALL"
    AddHandler btnAll.Click, AddressOf ScopeButtonClick
    f.Controls.Add(btnAll)

    Dim btnCancel As New WF.Button()
    btnCancel.Text = "Cancel"
    btnCancel.Width = 100
    btnCancel.Height = 30
    btnCancel.Left = 292
    btnCancel.Top = 65
    btnCancel.Tag = ""
    AddHandler btnCancel.Click, AddressOf ScopeButtonClick
    f.Controls.Add(btnCancel)

    f.ShowDialog()

    If f.Tag Is Nothing Then
        ShowRemoveTagScopeForm = ""
    Else
        ShowRemoveTagScopeForm = CStr(f.Tag)
    End If

End Function

Private Sub ScopeButtonClick(sender As Object, E As System.EventArgs)

    Dim btn As WF.Button = TryCast(sender, WF.Button)

    If btn Is Nothing Then Exit Sub

    Dim f As WF.Form = btn.FindForm()

    If f Is Nothing Then Exit Sub

    f.Tag = CStr(btn.Tag)
    f.Close()

End Sub

Private Function RemoveTagFromSpecificComponent(activeDoc As INV.Document, tagNs As String) As Integer

    If activeDoc Is Nothing Then Return 0

    If activeDoc.DocumentType = INV.DocumentTypeEnum.kPartDocumentObject OrElse activeDoc.DocumentType = INV.DocumentTypeEnum.kAssemblyDocumentObject Then

        Dim removed As Integer = RemoveTagFromDocument(activeDoc, tagNs)

        Try
            activeDoc.Save()
        Catch
        End Try

        Return removed

    End If

    Return 0

End Function

Private Function RemoveTagsFromAllComponents(topAsm As INV.AssemblyDocument, tagNs As String) As Integer

    Dim removedCount As Integer = 0

    removedCount += RemoveTagFromDocument(topAsm, tagNs)

    Dim d As INV.Document

    For Each d In topAsm.AllReferencedDocuments

        If d Is Nothing Then Continue For
        If String.IsNullOrEmpty(d.FullFileName) Then Continue For

        If d.DocumentType = INV.DocumentTypeEnum.kPartDocumentObject OrElse d.DocumentType = INV.DocumentTypeEnum.kAssemblyDocumentObject Then

            removedCount += RemoveTagFromDocument(d, tagNs)

            Try
                d.Save()
            Catch
            End Try

        End If

    Next

    Try
        topAsm.Save()
    Catch
    End Try

    Return removedCount

End Function

Private Function RemoveTagFromDocument(doc As INV.Document, tagNs As String) As Integer

    Dim removedCount As Integer = 0

    On Error Resume Next

    Dim docSets As INV.AttributeSets = doc.AttributeSets
    Dim docSet As INV.AttributeSet = docSets.Item(tagNs)

    If Err.Number = 0 AndAlso docSet IsNot Nothing Then
        docSet.Delete()
        removedCount += 1
    End If

    Err.Clear()

    If doc.DocumentType = INV.DocumentTypeEnum.kPartDocumentObject Then

        Dim p As INV.PartDocument = TryCast(doc, INV.PartDocument)

        If p IsNot Nothing Then

            Dim partSets As INV.AttributeSets = p.ComponentDefinition.AttributeSets
            Dim partSet As INV.AttributeSet = partSets.Item(tagNs)

            If Err.Number = 0 AndAlso partSet IsNot Nothing Then
                partSet.Delete()
                removedCount += 1
            End If

            Err.Clear()

        End If

    ElseIf doc.DocumentType = INV.DocumentTypeEnum.kAssemblyDocumentObject Then

        Dim asm As INV.AssemblyDocument = TryCast(doc, INV.AssemblyDocument)

        If asm IsNot Nothing Then

            Dim asmSets As INV.AttributeSets = asm.ComponentDefinition.AttributeSets
            Dim asmSet As INV.AttributeSet = asmSets.Item(tagNs)

            If Err.Number = 0 AndAlso asmSet IsNot Nothing Then
                asmSet.Delete()
                removedCount += 1
            End If

            Err.Clear()

        End If

    End If

    On Error GoTo 0

    Return removedCount

End Function

Private Function PickPartFeature(prompt As String) As Object

    Dim picked As Object = Nothing

    Try
        picked = ThisApplication.CommandManager.Pick(INV.SelectionFilterEnum.kPartFeatureFilter, prompt)
    Catch
        picked = Nothing
    End Try

    PickPartFeature = picked

End Function

Private Function GetFeatureName(featureObj As Object) As String

    On Error Resume Next

    Dim nm As String = CStr(CallByName(featureObj, "Name", CallType.Get))

    If Err.Number <> 0 Then
        Err.Clear()
        GetFeatureName = ""
    Else
        GetFeatureName = nm
    End If

    On Error GoTo 0

End Function

Private Function GetDetectedTagText(activeDoc As INV.Document, tagNs As String, tagKey As String) As String

    If activeDoc Is Nothing Then Return ""

    Dim docTag As String = GetTagValue(activeDoc, tagNs, tagKey)
    Dim defTag As String = ""

    If activeDoc.DocumentType = INV.DocumentTypeEnum.kPartDocumentObject Then

        Dim p As INV.PartDocument = TryCast(activeDoc, INV.PartDocument)

        If p IsNot Nothing Then
            defTag = GetTagValue(p.ComponentDefinition, tagNs, tagKey)
        End If

    ElseIf activeDoc.DocumentType = INV.DocumentTypeEnum.kAssemblyDocumentObject Then

        Dim asm As INV.AssemblyDocument = TryCast(activeDoc, INV.AssemblyDocument)

        If asm IsNot Nothing Then
            defTag = GetTagValue(asm.ComponentDefinition, tagNs, tagKey)
        End If

    End If

    If Not String.IsNullOrWhiteSpace(docTag) AndAlso Not String.IsNullOrWhiteSpace(defTag) Then

        If String.Compare(docTag, defTag, True) = 0 Then
            Return docTag
        Else
            Return "Document: " & docTag & " | Definition: " & defTag
        End If

    ElseIf Not String.IsNullOrWhiteSpace(docTag) Then

        Return "Document: " & docTag

    ElseIf Not String.IsNullOrWhiteSpace(defTag) Then

        Return "Definition: " & defTag

    End If

    Return "No internal CAD tag detected"

End Function

Private Function ResolveEffectiveTagForActiveFile(activeDoc As INV.Document, tagNs As String, tagKey As String, typedTag As String) As String

    If activeDoc Is Nothing Then Return typedTag

    Dim foundTags As New List(Of String)

    Dim docTag As String = GetTagValue(activeDoc, tagNs, tagKey)

    If Not String.IsNullOrWhiteSpace(docTag) Then
        If Not foundTags.Contains(docTag) Then foundTags.Add(docTag)
    End If

    If activeDoc.DocumentType = INV.DocumentTypeEnum.kPartDocumentObject Then

        Dim p As INV.PartDocument = TryCast(activeDoc, INV.PartDocument)

        If p IsNot Nothing Then
            Dim defTag As String = GetTagValue(p.ComponentDefinition, tagNs, tagKey)

            If Not String.IsNullOrWhiteSpace(defTag) Then
                If Not foundTags.Contains(defTag) Then foundTags.Add(defTag)
            End If
        End If

    ElseIf activeDoc.DocumentType = INV.DocumentTypeEnum.kAssemblyDocumentObject Then

        Dim asm As INV.AssemblyDocument = TryCast(activeDoc, INV.AssemblyDocument)

        If asm IsNot Nothing Then
            Dim defTag As String = GetTagValue(asm.ComponentDefinition, tagNs, tagKey)

            If Not String.IsNullOrWhiteSpace(defTag) Then
                If Not foundTags.Contains(defTag) Then foundTags.Add(defTag)
            End If
        End If

    End If

    If foundTags.Count = 0 Then
        Return typedTag
    End If

    If foundTags.Count = 1 Then
        Return foundTags(0)
    End If

    Return ShowTagChoiceForm(foundTags, typedTag)

End Function

Private Function ShowTagChoiceForm(foundTags As List(Of String), typedTag As String) As String

    Dim f As New WF.Form()
    f.Text = "Choose Internal CAD Tag"
    f.FormBorderStyle = WF.FormBorderStyle.FixedDialog
    f.StartPosition = WF.FormStartPosition.CenterParent
    f.MinimizeBox = False
    f.MaximizeBox = False
    f.Width = 460
    f.Height = 230

    Dim lbl As New WF.Label()
    lbl.Left = 12
    lbl.Top = 14
    lbl.Width = 420
    lbl.Text = "Multiple tags were detected. Choose which tag to use for this action."
    f.Controls.Add(lbl)

    Dim cbo As New WF.ComboBox()
    cbo.Left = 12
    cbo.Top = 48
    cbo.Width = 420
    cbo.DropDownStyle = WF.ComboBoxStyle.DropDownList

    Dim tagValue As String
    For Each tagValue In foundTags
        cbo.Items.Add(tagValue)
    Next

    If Not String.IsNullOrWhiteSpace(typedTag) Then
        cbo.Items.Add(typedTag)
    End If

    If cbo.Items.Count > 0 Then cbo.SelectedIndex = 0

    f.Controls.Add(cbo)

    Dim okBtn As New WF.Button()
    okBtn.Text = "OK"
    okBtn.Width = 90
    okBtn.Height = 28
    okBtn.Left = 242
    okBtn.Top = 125
    okBtn.DialogResult = WF.DialogResult.OK
    f.Controls.Add(okBtn)

    Dim cancelBtn As New WF.Button()
    cancelBtn.Text = "Cancel"
    cancelBtn.Width = 90
    cancelBtn.Height = 28
    cancelBtn.Left = 342
    cancelBtn.Top = 125
    cancelBtn.DialogResult = WF.DialogResult.Cancel
    f.Controls.Add(cancelBtn)

    f.AcceptButton = okBtn
    f.CancelButton = cancelBtn

    If f.ShowDialog() = WF.DialogResult.OK Then
        Return CStr(cbo.SelectedItem)
    End If

    Return ""

End Function
